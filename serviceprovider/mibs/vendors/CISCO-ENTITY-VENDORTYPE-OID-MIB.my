-- *****************************************************************
-- CISCO-ENTITY-VENDORTYPE-OID-MIB.my: OID assignments for Cisco components
-- for use by the ENTITY-MIB
--   

-- August 1997, Ramanathan R. Kavasseri
--   
-- Copyright (c) 1997-2013 by cisco Systems, Inc.
-- All rights reserved.
-- *****************************************************************

CISCO-ENTITY-VENDORTYPE-OID-MIB DEFINITIONS ::= BEGIN

IMPORTS
    MODULE-IDENTITY
        FROM SNMPv2-SMI
    ciscoModules
        FROM CISCO-SMI;


ciscoEntityVendortypeOIDMIB MODULE-IDENTITY
    LAST-UPDATED    "201311270000Z"
    ORGANIZATION    "Cisco Systems, Inc."
    CONTACT-INFO
            "Cisco Systems
            Customer Service

            Postal: 170 W Tasman Drive
            San Jose, CA  95134
            USA

            Tel: +1 800 553-NETS

            E-mail: cs-snmp@cisco.com"
    DESCRIPTION
        "This module defines the object identifiers that are
        assigned to various components on cisco products,
        which are used by the entPhysicalTable of the ENTITY-MIB
        to uniquely identify the type of each physical entry."
    REVISION        "201311270000Z"
    DESCRIPTION
        "Added following OIDs:
        cevChassisME6340ACA, cevChassisME6340DCA,
        cevChassisME6340DCB, cevChassisCat296024TT,
        cevChassisCat296048TT, cevContainerFabric13Slot,
        cevPowerSupply6340PWRDC, cevPowerSupply6340PWRAC,
        cevFanTrayUbr10012, cevPowerSupplyUbr10012AC,
        cevPowerSupplyUbr10012DC, cevVwic2T1E1Ran,
        cevModuleCat296024TT,cevModuleCat296048TT
        cevCat6kMsfc2a, cevCat6kWs6340Sup,
        cevCat6kWs6340LcA, cevCat6kWs6340LcB,
        cevPortAdslAnnexA, cevPortAdslAnnexB"
    REVISION        "200504280930Z"
    DESCRIPTION
        "Added following OIDs:
        cevUbrTccPlus"
    REVISION        "200504181930Z"
    DESCRIPTION
        "Added following OIDs:
        cevChassisCat6kMsfc2a, cevChassisCe611K9
        cevContainer9513RearFanBay, cevNme16Es1GeNoPwr,
        cevNmeX24Es1GeNoPwr, cevNmeXd24Es2StNoPwr,
        cevNmeXd48Es2GeNoPwr, cevCpuCat6kMsfc2a,
        cevGsrCsc12404B, cevGsrCsc12406B,
        cevGsrCsc12410B, cevGsrCsc12416B,
        cevONS1553010G4ChASp, cevONS1553010G4ChBSp,
        cevONS1553010G4ChCSp, cevONS1553010G4ChDSp,
        cevONS1553010G4ChESp, cevONS1553010G4ChFSp,
        cevONS1553010G4ChGSp, cevONS1553010G4ChHSp,
        cevONS1553010G4ChA, cevONS1553010G4ChB,
        cevONS1553010G4ChC, cevONS1553010G4ChD,
        cevONS1553010G4ChE, cevONS1553010G4ChF,
        cevONS1553010G4ChG, cevONS1553010G4ChH,
        cevONS1553010G32ChSp, cevONS1553010G32Ch,
        cevSFPOc3smsr, cevSFPOc12smsr, cevSFPOc48mm."
    REVISION        "200204051400Z"
    DESCRIPTION
        "CANA Assignments."
    REVISION        "9708051930Z"
    DESCRIPTION
        "Miscellaneous updates."
    ::= { ciscoModules 3 }


cevMIBObjects  OBJECT IDENTIFIER
    ::= { ciscoEntityVendortypeOIDMIB 1 }

-- This MIB assigns OIDs for use as the values of entPhysicalVendorType.
-- The subtrees in which the OID values are assigned, are structured
-- into a hierarchy based on the values of RFC 2037's PhysicalClass
-- textual convention.  For reference, the definition of PhysicalClass
-- is as follows:
--   
-- PhysicalClass ::= TEXTUAL-CONVENTION
-- STATUS          current
-- DESCRIPTION
-- "An enumerated value which provides an indication of the
-- general hardware type of a particular physical entity."
-- SYNTAX      INTEGER  {
-- other(1),
-- unknown(2),
-- chassis(3),
-- backplane(4),
-- container(5),    e.g. slot or daughter-card holder
-- powerSupply(6),
-- fan(7),
-- sensor(8),
-- module(9),       e.g. plug-in card or daughter-card
-- port(10),
-- stack(11),
-- midplane(12)
-- }

cevOther  OBJECT IDENTIFIER
    ::= { cevMIBObjects 1 }

-- cevOther objects are partitioned into sub-groups based on
-- the functionality of the objects e.g., cpu-type cards have their
-- own sub-group, fabric cards have another sub-group etc.

cevOtherUnknownCard  OBJECT IDENTIFIER
    ::= { cevOther 1 }

cevOtherMoH  OBJECT IDENTIFIER
    ::= { cevOther 2 }

-- 1 port Music On Hold

cevNmeApaLink  OBJECT IDENTIFIER
    ::= { cevOther 3 }

-- Service Classification Element Link between Network side and Subscriber side for NME-APA.

cevOtherSce8000Scm  OBJECT IDENTIFIER
    ::= { cevOther 5 }

-- Cisco SCE8000 Service Control Module

cevOtherSce8000Sip  OBJECT IDENTIFIER
    ::= { cevOther 6 }

-- SPA Interface Processor for SCE8000

cevOtherCscLink  OBJECT IDENTIFIER
    ::= { cevOther 8 }

-- Service control entity link between subscriber side and user side

cevUnknown  OBJECT IDENTIFIER
    ::= { cevMIBObjects 2 }

cevChassis  OBJECT IDENTIFIER
    ::= { cevMIBObjects 3 }

-- chassis OID assignments

cevChassisUnknown  OBJECT IDENTIFIER
    ::= { cevChassis 1 }

cevChassis2000  OBJECT IDENTIFIER
    ::= { cevChassis 2 }

cevChassis2500  OBJECT IDENTIFIER
    ::= { cevChassis 3 }

cevChassis2501  OBJECT IDENTIFIER
    ::= { cevChassis 4 }

cevChassis2502  OBJECT IDENTIFIER
    ::= { cevChassis 5 }

cevChassis2503  OBJECT IDENTIFIER
    ::= { cevChassis 6 }

cevChassis2504  OBJECT IDENTIFIER
    ::= { cevChassis 7 }

cevChassis2505  OBJECT IDENTIFIER
    ::= { cevChassis 8 }

cevChassis2506  OBJECT IDENTIFIER
    ::= { cevChassis 9 }

cevChassis2507  OBJECT IDENTIFIER
    ::= { cevChassis 10 }

cevChassis2508  OBJECT IDENTIFIER
    ::= { cevChassis 11 }

cevChassis2509  OBJECT IDENTIFIER
    ::= { cevChassis 12 }

cevChassis2510  OBJECT IDENTIFIER
    ::= { cevChassis 13 }

cevChassis2511  OBJECT IDENTIFIER
    ::= { cevChassis 14 }

cevChassis2512  OBJECT IDENTIFIER
    ::= { cevChassis 15 }

cevChassis2513  OBJECT IDENTIFIER
    ::= { cevChassis 16 }

cevChassis2514  OBJECT IDENTIFIER
    ::= { cevChassis 17 }

cevChassis2515  OBJECT IDENTIFIER
    ::= { cevChassis 18 }

cevChassis2516  OBJECT IDENTIFIER
    ::= { cevChassis 19 }

cevChassis2517  OBJECT IDENTIFIER
    ::= { cevChassis 20 }

cevChassis2518  OBJECT IDENTIFIER
    ::= { cevChassis 21 }

cevChassis2519  OBJECT IDENTIFIER
    ::= { cevChassis 22 }

cevChassis2520  OBJECT IDENTIFIER
    ::= { cevChassis 23 }

cevChassis2521  OBJECT IDENTIFIER
    ::= { cevChassis 24 }

cevChassis2522  OBJECT IDENTIFIER
    ::= { cevChassis 25 }

cevChassis2523  OBJECT IDENTIFIER
    ::= { cevChassis 26 }

cevChassis2524  OBJECT IDENTIFIER
    ::= { cevChassis 27 }

cevChassis2525  OBJECT IDENTIFIER
    ::= { cevChassis 28 }

cevChassis3000  OBJECT IDENTIFIER
    ::= { cevChassis 29 }

cevChassis3104  OBJECT IDENTIFIER
    ::= { cevChassis 30 }

cevChassis3204  OBJECT IDENTIFIER
    ::= { cevChassis 31 }

cevChassisIGS  OBJECT IDENTIFIER
    ::= { cevChassis 32 }

cevChassis2501LANFRADFX  OBJECT IDENTIFIER
    ::= { cevChassis 33 }

cevChassis2501FRADFX  OBJECT IDENTIFIER
    ::= { cevChassis 34 }

cevChassis2502LANFRADFX  OBJECT IDENTIFIER
    ::= { cevChassis 35 }

cevChassisWSX3011  OBJECT IDENTIFIER
    ::= { cevChassis 36 }

cevChassisAccessProEC  OBJECT IDENTIFIER
    ::= { cevChassis 37 }

cevChassisAccessProRC  OBJECT IDENTIFIER
    ::= { cevChassis 38 }

cevChassisWSX5301  OBJECT IDENTIFIER
    ::= { cevChassis 39 }

cevChassisAS2509RJ  OBJECT IDENTIFIER
    ::= { cevChassis 40 }

cevChassisAS2511RJ  OBJECT IDENTIFIER
    ::= { cevChassis 41 }

cevChassis3800  OBJECT IDENTIFIER
    ::= { cevChassis 42 }

cevChassis3620  OBJECT IDENTIFIER
    ::= { cevChassis 43 }

cevChassis3640  OBJECT IDENTIFIER
    ::= { cevChassis 44 }

cevChassis7204  OBJECT IDENTIFIER
    ::= { cevChassis 45 }

cevChassis7206  OBJECT IDENTIFIER
    ::= { cevChassis 46 }

cevChassisAS5300  OBJECT IDENTIFIER
    ::= { cevChassis 47 }

cevChassisAs5800RS  OBJECT IDENTIFIER
    ::= { cevChassis 49 }

-- AS5800 Router Shelf

cevChassisAs5800DS  OBJECT IDENTIFIER
    ::= { cevChassis 50 }

-- AS5800 Dial Shelf

cevChassis7202  OBJECT IDENTIFIER
    ::= { cevChassis 51 }

-- Modular two slot router in the cisco7200 family

cevChassisRpm  OBJECT IDENTIFIER
    ::= { cevChassis 52 }

-- Router Processor Module

cevChassis1710  OBJECT IDENTIFIER
    ::= { cevChassis 53 }

-- VPN(Virtual Private Network) Security Router with 1 FastEthernet and 1 Ethernet interface onboard

cevChassis1720  OBJECT IDENTIFIER
    ::= { cevChassis 54 }

cevChassisCat8540Msr  OBJECT IDENTIFIER
    ::= { cevChassis 55 }

-- Catalyst 8540 Multiservice Switching Router

cevChassisCat8540Csr  OBJECT IDENTIFIER
    ::= { cevChassis 56 }

-- Catalyst 8540 Campus Switching Router

cevChassisUbr7246  OBJECT IDENTIFIER
    ::= { cevChassis 57 }

-- Universal Broadband Router

cevChassis7576  OBJECT IDENTIFIER
    ::= { cevChassis 58 }

-- Dual Independent RSP platform, 13 slots

cevChassis3660  OBJECT IDENTIFIER
    ::= { cevChassis 59 }

-- Six slot MARs router

cevChassis1401  OBJECT IDENTIFIER
    ::= { cevChassis 60 }

-- Router with 1 ethernet and 1 ATM25 interface

cevChassis2613  OBJECT IDENTIFIER
    ::= { cevChassis 61 }

-- c2600 chassis with 1 integrated token ring interface

cevChassis2610  OBJECT IDENTIFIER
    ::= { cevChassis 62 }

-- c2600 chassis with 1 integrated ethernet interface

cevChassis2612  OBJECT IDENTIFIER
    ::= { cevChassis 63 }

-- c2600 chassis with an integrated token ring and ethernet interface

cevChassis2611  OBJECT IDENTIFIER
    ::= { cevChassis 64 }

-- c2600 chassis with 2 integrated ethernet interfaces

cevChassis2620  OBJECT IDENTIFIER
    ::= { cevChassis 65 }

-- c2600 chassis with 1 integrated fast ethernet interface

cevChassis2621  OBJECT IDENTIFIER
    ::= { cevChassis 66 }

-- c2600 chassis with 2 integrated fast ethernet interfaces

cevChassisCat8510Csr  OBJECT IDENTIFIER
    ::= { cevChassis 67 }

-- Catalyst 8510 Campus Switching Router

cevChassisUbr7223  OBJECT IDENTIFIER
    ::= { cevChassis 68 }

-- Universal Broadband Router

cevChassis6400Nrp  OBJECT IDENTIFIER
    ::= { cevChassis 69 }

-- Cisco 6400 Network Routing Processor

cevChassis801  OBJECT IDENTIFIER
    ::= { cevChassis 70 }

-- Cisco 800 platform with 1 ethernet and 1 BRI S/T

cevChassis802  OBJECT IDENTIFIER
    ::= { cevChassis 71 }

-- Cisco 800 platform with 1 ethernet and 1 BRI U

cevChassis803  OBJECT IDENTIFIER
    ::= { cevChassis 72 }

-- Cisco 800 platform with 1 ethernet 4-port HUB, 1 BRI S/T, and 2 POTs

cevChassis804  OBJECT IDENTIFIER
    ::= { cevChassis 73 }

-- Cisco 800 platform with 1 ethernet 4-port HUB, 1 BRI U, and 2 POTs

cevChassis7206Vxr  OBJECT IDENTIFIER
    ::= { cevChassis 74 }

-- Cisco 7200 platform, VXR series chassis with 6 slots

cevChassis7204Vxr  OBJECT IDENTIFIER
    ::= { cevChassis 75 }

-- Cisco 7200 platform, VXR series chassis with 4 slots

cevChassis1750  OBJECT IDENTIFIER
    ::= { cevChassis 76 }

-- VoIP (Voice over IP) capable Cisco 1700 platform with 2 WIC/VIC slots and 1 VIC-only slot

cevChassisCat2924XLv  OBJECT IDENTIFIER
    ::= { cevChassis 77 }

-- Catalyst 2924XL switch with 24 10BaseT/100BaseTX autosensing switch ports; supports port-based VLANs; can run Standard or Enterprise edition software.

cevChassisCat2924CXLv  OBJECT IDENTIFIER
    ::= { cevChassis 78 }

-- Catalyst 2924C-XL switch with 22 10BaseT/100BaseTX and 2 100BaseFX autosensing switch ports; supports port-based VLANs; can run Standard or Enterprise edition software.

cevChassisCat2912XL  OBJECT IDENTIFIER
    ::= { cevChassis 79 }

-- Catalyst 2912XL switch with 12 10BaseT/100BaseTX autosensing switch ports, can run Standard or Enterprise edition software.

cevChassisCat2924MXL  OBJECT IDENTIFIER
    ::= { cevChassis 80 }

-- Catalyst 2924M-XL switch with 24 10BaseT/100BaseTX autosensing switch ports and 2 uplink slots, can run Standard or Enterprise edition software.

cevChassisCat2912MfXL  OBJECT IDENTIFIER
    ::= { cevChassis 81 }

-- Catalyst 2912MF-XL switch with 12 100BaseFX autosensing switch ports and 2 uplink slots. Switch can run only enterprise edition software.

cevChassis1538M  OBJECT IDENTIFIER
    ::= { cevChassis 82 }

-- Cisco Network Office 8-port 10/100 Stackable Repeater

cevChassis1548M  OBJECT IDENTIFIER
    ::= { cevChassis 83 }

-- Cisco Network Office 10/100 Stackable Switch

cevChassisFasthub100  OBJECT IDENTIFIER
    ::= { cevChassis 84 }

-- Cisco Fast Hub 100 Series 10/100 Stackable Repeater

cevChassisPIXFirewall  OBJECT IDENTIFIER
    ::= { cevChassis 85 }

-- Cisco PIX Firewall

cevChassisMGX8850  OBJECT IDENTIFIER
    ::= { cevChassis 86 }

-- Cisco Multiservice Gigabit Switch with 32 half height slots

cevChassisMGX8820  OBJECT IDENTIFIER
    ::= { cevChassis 87 }

-- Cisco Multiservice Gigabit Switch with 7 slots

cevChassisCat8510Msr  OBJECT IDENTIFIER
    ::= { cevChassis 88 }

-- Catalyst ATM 8510 Multiservice Switching Router

cevChassisCat8515Msr  OBJECT IDENTIFIER
    ::= { cevChassis 89 }

-- Catalyst ATM 8515 Multiservice Switching Router

cevChassisIGX8410  OBJECT IDENTIFIER
    ::= { cevChassis 90 }

-- Cisco IGX8400 (Integrated Gigabit eXchange) series wide-area switch with 8 slots

cevChassisIGX8420  OBJECT IDENTIFIER
    ::= { cevChassis 91 }

-- Cisco IGX8400 (Integrated Gigabit eXchange) series wide-area switch with 16 slots

cevChassisIGX8430  OBJECT IDENTIFIER
    ::= { cevChassis 92 }

-- Cisco IGX8400 (Integrated Gigabit eXchange) series wide-area switch with 32 slots

cevChassisIGX8450  OBJECT IDENTIFIER
    ::= { cevChassis 93 }

-- Cisco IGX8400 (Integrated Gigabit eXchange) series wide-area switch with integrated MGX feeder

cevChassisBPX8620  OBJECT IDENTIFIER
    ::= { cevChassis 95 }

-- Cisco BPX8600 (Broadband Packet eXchange) series wide-area switch with 15 slots

cevChassisBPX8650  OBJECT IDENTIFIER
    ::= { cevChassis 96 }

-- Cisco BPX8600 (Broadband Packet eXchange) series wide-area switch with integrated tag switching controller and 15 slots

cevChassisBPX8680  OBJECT IDENTIFIER
    ::= { cevChassis 97 }

-- Cisco BPX8600 (Broadband Packet eXchange) series wide-area switch with integrated MGX feeder and 15 slots

cevChassisCacheEngine  OBJECT IDENTIFIER
    ::= { cevChassis 98 }

-- Cisco Cache Engine

cevChassisCat6000  OBJECT IDENTIFIER
    ::= { cevChassis 99 }

-- Cisco Catalyst 6000

cevChassisMC3810  OBJECT IDENTIFIER
    ::= { cevChassis 100 }

-- Cisco Multiservice Access Concentrator 3800 series

cevChassisIGXSes  OBJECT IDENTIFIER
    ::= { cevChassis 102 }

-- Cisco IGX (Integrated Gigabit eXchange) Service Expansion Slot controller/feeder, used in IGX8410/IGX8420/IGX8430 switches.

cevChassisLocalDirector  OBJECT IDENTIFIER
    ::= { cevChassis 103 }

-- Cisco Local Director

cevChassis805  OBJECT IDENTIFIER
    ::= { cevChassis 104 }

-- Cisco 800 platform with 1 ethernet and 1 serial WIC

cevChassisCat3508GXL  OBJECT IDENTIFIER
    ::= { cevChassis 105 }

-- Cisco Catalyst 3508G-XL 8 GBIC Gigabit Port Switch, can run Standard or Enterprise edition software.

cevChassisCat3512XL  OBJECT IDENTIFIER
    ::= { cevChassis 106 }

-- Cisco Catalyst 3512XL switch with 12 10/100BaseTX and 2 GBIC Gigabit ports, can run Standard or Enterprise edition software.

cevChassisCat3524XL  OBJECT IDENTIFIER
    ::= { cevChassis 107 }

-- Cisco Catalyst 3524XL switch with 24 10/100BaseTX and 2 GBIC Gigabit ports, can run Standard or Enterprise edition software.

cevChassisCat2908XL  OBJECT IDENTIFIER
    ::= { cevChassis 108 }

-- Cisco Catalyst 2900XL series 8 port 10/100BaseTX switch

cevChassisCat2916MXL  OBJECT IDENTIFIER
    ::= { cevChassis 109 }

-- Cisco Catalyst 2916M-XL 16 port 10/100BaseTX switch with 2 uplink slots

cevChassis1417  OBJECT IDENTIFIER
    ::= { cevChassis 111 }

-- Cisco 1400 series router with 1 Ethernet and 1 ADSL interface, with 1417 chipset

cevChassisOpticalRegenerator  OBJECT IDENTIFIER
    ::= { cevChassis 112 }

-- Cisco Optical Regenerator

cevChassis6100  OBJECT IDENTIFIER
    ::= { cevChassis 113 }

-- Cisco 6100 DSLAM Chassis

cevChassis6130  OBJECT IDENTIFIER
    ::= { cevChassis 114 }

-- Cisco 6130 DSLAM Chassis

cevChassis6260  OBJECT IDENTIFIER
    ::= { cevChassis 115 }

-- Cisco 6260 DSLAM Chassis

cevChassisCat2924XL  OBJECT IDENTIFIER
    ::= { cevChassis 116 }

-- Cisco Catalyst 2924XL with 24 10/100BaseTX switch ports; does not support port-based VLANs.

cevChassisCat2924CXL  OBJECT IDENTIFIER
    ::= { cevChassis 117 }

-- Cisco Catalyst 2924C-XL; does not support port-based VLANs.

cevChassisUbr924  OBJECT IDENTIFIER
    ::= { cevChassis 118 }

-- Cisco UBR Cable Modem which is a UBR904 with 2 FXS Voice ports

cevChassisWsX6302Msm  OBJECT IDENTIFIER
    ::= { cevChassis 119 }

-- Catalyst 6000 or 6500 Series Multilayer Switch Module WS-X6302-MSM that directly interfaces to the switch's backplane to provide layer 3 switching.

cevChassisCat5kRsfc  OBJECT IDENTIFIER
    ::= { cevChassis 120 }

-- Catalyst 5000 Routing Switching Feature Card that is treated as a standalone system by the NMS

cevChassis7120Quadt1  OBJECT IDENTIFIER
    ::= { cevChassis 122 }

-- 7120 Series chassis with 2 10/100 FE interfaces, 4 T1/E1 interfaces

cevChassis7120T3  OBJECT IDENTIFIER
    ::= { cevChassis 123 }

-- 7120 Series chassis with 2 10/100 FE interfaces, 1 T3 interface

cevChassis7120E3  OBJECT IDENTIFIER
    ::= { cevChassis 124 }

-- 7120 Series chassis with 2 10/100 FE interfaces, 1 E3 interface

cevChassis7120At3  OBJECT IDENTIFIER
    ::= { cevChassis 125 }

-- 7120 Series chassis with 2 10/100 FE interfaces, 1 T3 ATM interface

cevChassis7120Ae3  OBJECT IDENTIFIER
    ::= { cevChassis 126 }

-- 7120 Series chassis with 2 10/100 FE interfaces, 1 E3 ATM interface

cevChassis7120Smi3  OBJECT IDENTIFIER
    ::= { cevChassis 127 }

-- 7120 Series chassis with 2 10/100 FE interfaces, 1 OC3SMI ATM interface

cevChassis7140Dualt3  OBJECT IDENTIFIER
    ::= { cevChassis 128 }

-- 7140 Series chassis with 2 10/100 FE interfaces, 2 T3 interfaces

cevChassis7140Duale3  OBJECT IDENTIFIER
    ::= { cevChassis 129 }

-- 7140 Series chassis with 2 10/100 FE interfaces, 2 E3 interfaces

cevChassis7140Dualat3  OBJECT IDENTIFIER
    ::= { cevChassis 130 }

-- 7140 Series chassis with 2 10/100 FE interfaces, 2 T3 ATM interfaces

cevChassis7140Dualae3  OBJECT IDENTIFIER
    ::= { cevChassis 131 }

-- 7140 Series chassis with 2 10/100 FE interfaces, 2 E3 ATM interfaces

cevChassis7140Dualmm3  OBJECT IDENTIFIER
    ::= { cevChassis 132 }

-- 7140 Series chassis with 2 10/100 FE interfaces, 2 OC3MM ATM interfaces

cevChassis827QuadV  OBJECT IDENTIFIER
    ::= { cevChassis 133 }

-- Cisco 800 platform with 1 ethernet, 1 ADSL DMT issue 2, and 4 voice POTS FXS ports

cevChassisUbr7246Vxr  OBJECT IDENTIFIER
    ::= { cevChassis 134 }

-- Cisco 7246 Universal Broadband Router, VXR series

cevChassis12016  OBJECT IDENTIFIER
    ::= { cevChassis 136 }

-- Cisco 12000 platform with 16 slots

cevChassisAs5400  OBJECT IDENTIFIER
    ::= { cevChassis 137 }

-- Cisco AS5400

cevChassis7140Octt1  OBJECT IDENTIFIER
    ::= { cevChassis 138 }

-- 7140 Series chassis with 8 integrated T1/E1 serial ports

cevChassis7140Dualfe  OBJECT IDENTIFIER
    ::= { cevChassis 139 }

-- 7140 Series chassis with 2 integrated 10/100 FE interfaces

cevChassisCat3548XL  OBJECT IDENTIFIER
    ::= { cevChassis 140 }

-- Catalyst 3548XL switch (WS-C3548-XL)

cevChassisCat6006  OBJECT IDENTIFIER
    ::= { cevChassis 141 }

-- Catalyst 6000 with 6 slots

cevChassisCat6009  OBJECT IDENTIFIER
    ::= { cevChassis 142 }

-- Catalyst 6000 with 9 slots

cevChassisCat6506  OBJECT IDENTIFIER
    ::= { cevChassis 143 }

-- Catalyst 6000 Plus with 6 slots

cevChassisCat6509  OBJECT IDENTIFIER
    ::= { cevChassis 144 }

-- Catalyst 6000 Plus with 9 slots

cevChassis827  OBJECT IDENTIFIER
    ::= { cevChassis 145 }

-- Cisco 800 platform with 1 ethernet, 1 ADSL DMT issue 2

cevChassisAS5200  OBJECT IDENTIFIER
    ::= { cevChassis 146 }

-- Cisco AS5200

cevChassis12008  OBJECT IDENTIFIER
    ::= { cevChassis 147 }

-- Cisco GSR 12008

cevChassis12012  OBJECT IDENTIFIER
    ::= { cevChassis 148 }

-- Cisco GSR 12012

cevChassisMc3810V3  OBJECT IDENTIFIER
    ::= { cevChassis 149 }

-- Cisco MC3810-V3, capable of data, voice and video.  Supports 2 additional ports than the MC3810-V, used for optional access cards.

cevChassis7507z  OBJECT IDENTIFIER
    ::= { cevChassis 151 }

-- Cisco 7507z chassis, Czbus capable, 7 slots

cevChassis7513z  OBJECT IDENTIFIER
    ::= { cevChassis 152 }

-- Cisco 7513z chassis, Czbus capable, 13 slots

cevChassis7507mx  OBJECT IDENTIFIER
    ::= { cevChassis 153 }

-- Cisco 7507mx chassis, Czbus capable, TDM (Time Division Multiplexing) backplane support, 7 slots

cevChassis7513mx  OBJECT IDENTIFIER
    ::= { cevChassis 154 }

-- Cisco 7513mx chassis, Czbus capable, TDM (Time Division Multiplexing) backplane support, 13 slots

cevChassisUbr912C  OBJECT IDENTIFIER
    ::= { cevChassis 155 }

-- Cisco uBR912-C Cable Modem with CSU/DSU WIC

cevChassisUbr912S  OBJECT IDENTIFIER
    ::= { cevChassis 156 }

-- Cisco uBR912-S Cable Modem with Serial WIC

cevChassisUbr914  OBJECT IDENTIFIER
    ::= { cevChassis 157 }

-- Cisco uBR914 Cable Modem with removable WIC

cevChassis6160  OBJECT IDENTIFIER
    ::= { cevChassis 160 }

-- Cisco 6160 DSLAM chassis

cevChassisCat2948gL3  OBJECT IDENTIFIER
    ::= { cevChassis 161 }

-- Catalyst 2948G-L3 (WS-C2948G-L3) Mid-range fixed configuration layer 3 switch with 48 10/100 ethernet ports and 2 GBIC based Gigabit Ethernet ports

cevChassisCat4232L3  OBJECT IDENTIFIER
    ::= { cevChassis 164 }

-- Cisco Catalyst 4232-L3 layer 3 line card that is treated as a standalone system by the NMS

cevChassisOpticalRegeneratorDCPower  OBJECT IDENTIFIER
    ::= { cevChassis 165 }

-- Cisco Optical Regenerator with a DC power supply

cevChassisCVA122  OBJECT IDENTIFIER
    ::= { cevChassis 171 }

-- Cisco CVA122 Cable Voice Adapter (Residential Cable Modem with two voice ports)

cevChassisCVA124  OBJECT IDENTIFIER
    ::= { cevChassis 172 }

-- Cisco CVA124 Cable Voice Adapter (Residential Cable Modem with four voice ports)

cevChassisAs5850  OBJECT IDENTIFIER
    ::= { cevChassis 173 }

-- High End Dial Access Server

cevChassisMGX8240  OBJECT IDENTIFIER
    ::= { cevChassis 176 }

-- High Density Circuit Emulation Service Gateway chassis with two shelf controller slots and fifteen Service Modulesfor Private Line Service

cevChassisAs5350  OBJECT IDENTIFIER
    ::= { cevChassis 178 }

-- Cisco low end Access server platform

cevChassisMGX8950  OBJECT IDENTIFIER
    ::= { cevChassis 181 }

-- Cisco Multiservice Gigabit Switch(180Gb) Chassis with 32 half height slots

cevChassisUbr925  OBJECT IDENTIFIER
    ::= { cevChassis 182 }

-- Cisco UBR925 Cable Modem/Router with VOIP and hardware accelerated IPSEC

cevChassisUbr10012  OBJECT IDENTIFIER
    ::= { cevChassis 183 }

-- Cisco uBR10000 platform with 8 broadband slots and 4 WAN slots

cevChassisCat4kGateway  OBJECT IDENTIFIER
    ::= { cevChassis 184 }

-- Catalyst 4000 Access Gateway line card supporting voice and WAN (Wide Area Network) interfaces as well as conferencing and transcoding services for operation with the Cisco Call Manager

cevChassis120168r  OBJECT IDENTIFIER
    ::= { cevChassis 185 }

-- Teracore ready 8 rail chassis for Cisco 12000 platform

cevChassis2650  OBJECT IDENTIFIER
    ::= { cevChassis 186 }

-- c2650 platform with 1 integrated fast ethernet interface

cevChassis2651  OBJECT IDENTIFIER
    ::= { cevChassis 187 }

-- c2650 platform with 2 integrated fast ethernet interfaces

cevChassis826  OBJECT IDENTIFIER
    ::= { cevChassis 189 }

-- Cisco 800 platform with 1 ethernet, 1 ADSL over ISDN

cevChassisCat295012  OBJECT IDENTIFIER
    ::= { cevChassis 190 }

-- Cisco Catalyst c2950 switch with 12 10/100BaseTX ports (WS-c2950-12)

cevChassisCat295024  OBJECT IDENTIFIER
    ::= { cevChassis 191 }

-- Cisco Catalyst c2950 switch with 24 10/100 BaseTX ports  (WS-c2950-24)

cevChassis1751  OBJECT IDENTIFIER
    ::= { cevChassis 193 }

-- Digital voice capable Cisco 1700 platform with 2 WIC/VIC slots and 1 VIC-only slot

cevChassis1730Iad8Fxs  OBJECT IDENTIFIER
    ::= { cevChassis 194 }

-- Cisco 1700 class IAD (Integrated Access Device) with 8 FXS (Foreign Exchange Station) ports and DSL (Digital Subscriber Line) WIC

cevChassis1730Iad16Fxs  OBJECT IDENTIFIER
    ::= { cevChassis 195 }

-- Cisco 1700 class IAD (Integrated Access Device) with 16 FXS (Foreign Exchange Station) ports and DSL (Digital Subscriber Line) WIC

cevChassis626  OBJECT IDENTIFIER
    ::= { cevChassis 196 }

-- Cisco 600 DSL CPE pltaform with ADSL, DMT issue 1, 25M ATM interface

cevChassis627  OBJECT IDENTIFIER
    ::= { cevChassis 197 }

-- Cisco 600 DSL CPE pltaform with ADSL, DMT issue 2, 25M ATM interface

cevChassis633  OBJECT IDENTIFIER
    ::= { cevChassis 198 }

-- Cisco 600 DSL CPE platform with SDSL, 2B1Q line coding, serial interface (V.35/X.21)

cevChassis673  OBJECT IDENTIFIER
    ::= { cevChassis 199 }

-- Cisco 600 DSL CPE platform with SDSL, 2B1Q line coding, ethernet interface

cevChassis675  OBJECT IDENTIFIER
    ::= { cevChassis 200 }

-- Cisco 600 DSL CPE platform with ADSL, CAP, ethernet interface, POTS connector

cevChassis675e  OBJECT IDENTIFIER
    ::= { cevChassis 201 }

-- Cisco 600 DSL CPE platform with ADSL, CAP, ethernet interface, universal power supply

cevChassis676  OBJECT IDENTIFIER
    ::= { cevChassis 202 }

-- Cisco 600 DSL CPE platform with ADSL, DMT issue 1, ethernet interface

cevChassis677  OBJECT IDENTIFIER
    ::= { cevChassis 203 }

-- Cisco 600 DSL CPE platform with ADSL, DMT issue 2, ethernet interface

cevChassis678  OBJECT IDENTIFIER
    ::= { cevChassis 204 }

-- Cisco 600 DSL CPE platform with ADSL, CAP/DMT/G.Lite, ethernet interface

cevChassis3661Ac  OBJECT IDENTIFIER
    ::= { cevChassis 205 }

-- 1 Fast Ethernet version of c3660 with a AC power supply

cevChassis3661Dc  OBJECT IDENTIFIER
    ::= { cevChassis 206 }

-- 1 Fast Ethernet version of c3660 with a DC power supply

cevChassis3662Ac  OBJECT IDENTIFIER
    ::= { cevChassis 207 }

-- 2 Fast Ethernet version of c3660 with a AC power supply

cevChassis3662Dc  OBJECT IDENTIFIER
    ::= { cevChassis 208 }

-- 2 Fast Ethernet version of c3660 with a DC power supply

cevChassis3662AcCo  OBJECT IDENTIFIER
    ::= { cevChassis 209 }

-- 2 Fast Ethernet version of c3660 with a AC power supply for Telco's

cevChassis3662DcCo  OBJECT IDENTIFIER
    ::= { cevChassis 210 }

-- 2 Fast Ethernet version of c3660 with a DC power supply for Telco's

cevChassisUbr7111  OBJECT IDENTIFIER
    ::= { cevChassis 211 }

-- Low-end version of the Universal Broadband Router with 1 PA slot, 1 fixed RF line card (MC11C) and integrated upconvertor, designed for hotels, MDUs and smaller cable operators

cevChassisUbr7114  OBJECT IDENTIFIER
    ::= { cevChassis 213 }

-- Low-end version of the Universal Broadband Router with 1 PA slot, 1 fixed RF line card (MC14C) and integrated upconvertor, designed for hotels, MDUs and smaller cable operators

cevChassis12010  OBJECT IDENTIFIER
    ::= { cevChassis 215 }

-- Cisco 12000 platform with 10 slots

cevChassis8110  OBJECT IDENTIFIER
    ::= { cevChassis 216 }

-- Cisco 8110 (ATM network termination device) with 3 Line Interface module slots

cevChassisSOHO77  OBJECT IDENTIFIER
    ::= { cevChassis 220 }

-- Cisco SOHO (Small Office Home Office) ADSL Router, 1 Ethernet and 1 ADSL G.992.1 (G.DMT) and G.992.2 (G.Lite) Interface

cevChassisSOHO76  OBJECT IDENTIFIER
    ::= { cevChassis 221 }

-- Cisco SOHO (Small Office Home Office) ADSL over ISDN Router, 1 Ethernet and 1 ADSL ETSI/ITU-T G.992.1 Annex B (G.DMT) Interface

cevChassis7150Dualfe  OBJECT IDENTIFIER
    ::= { cevChassis 222 }

-- 7150 Series chassis with 2 integrated 10/100 FE interfaces

cevChassis7150Octt1  OBJECT IDENTIFIER
    ::= { cevChassis 223 }

-- 7150 Series chassis with 8 integrated T1/E1 serial ports

cevChassis7150Dualt3  OBJECT IDENTIFIER
    ::= { cevChassis 224 }

-- 7150 Series chassis with 2 10/100 FE interfaces, 2 T3 interfaces

cevChassisCat2950t24  OBJECT IDENTIFIER
    ::= { cevChassis 226 }

-- Cisco Catalyst c2950 switch with 24 10/100BaseT ports and 2 10/100/1000BaseT ports

cevChassisVPS1110  OBJECT IDENTIFIER
    ::= { cevChassis 227 }

-- Cisco VLAN Policy Server 1110 manages VLAN-based policies to control user access to a LAN, leveraging existing authentication mechanisms such as Windows Domain Controllers and Novell's NDS. This policy server is part of CiscoWorks2000 User Registration Tool product.

cevChassisContentEngine  OBJECT IDENTIFIER
    ::= { cevChassis 228 }

-- Cisco Content Engine Chassis.  The Cisco Content Engine is a Content Networking product that accelerates content delivery, ensuring maximum scalability and availability of content.  The Content Engines offer caching, Content Delivery Network (CDN) services, employee internet management (e.g., URL filtering) and proxy services

cevChassisIAD2420  OBJECT IDENTIFIER
    ::= { cevChassis 229 }

-- Integrated Access Device 2420 (IAD2420) chassis with Analog (8/16) FXS ports with T1 or ADSL (Asymmetrical Digital Subscriber Line) Uplinks

cevChassis677i  OBJECT IDENTIFIER
    ::= { cevChassis 230 }

-- Cisco 600 DSL CPE platform with ASDL, DMT issue 2 over ISDN, ethernet interface

cevChassis674  OBJECT IDENTIFIER
    ::= { cevChassis 231 }

-- Cisco 600 DSL CPE platform with G.SHDSL, ethernet interface

cevChassisDPA7630  OBJECT IDENTIFIER
    ::= { cevChassis 232 }

-- The Cisco Digital PBX Adapter (DPA) enables the integration of Cisco Call Manager with Octel voice mail systems

cevChassisCat355024  OBJECT IDENTIFIER
    ::= { cevChassis 233 }

-- Catalyst 3550 24 10/100 ports + 2 Gig uplinks fixed configuration Layer 2/Layer 3 Ethernet Switch

cevChassisCat355048  OBJECT IDENTIFIER
    ::= { cevChassis 234 }

-- Catalyst 3550 48 10/100 ports + 2 Gig uplinks fixed configuration Layer 2/Layer 3 Ethernet Switch

cevChassisCat355012T  OBJECT IDENTIFIER
    ::= { cevChassis 235 }

-- Catalyst 3550 12 1000T ports fixed configuration Layer 2/Layer 3 Ethernet Switch

cevChassisCVA122E  OBJECT IDENTIFIER
    ::= { cevChassis 238 }

-- Cisco CVA122-e Cable Voice Adapter(Residential Cable Modem with two voice ports)- European version

cevChassisCVA124E  OBJECT IDENTIFIER
    ::= { cevChassis 239 }

-- Cisco CVA124-e Cable Voice Adapter(Residential Cable Modem with four voice ports)- European version

cevChassisURM  OBJECT IDENTIFIER
    ::= { cevChassis 240 }

-- Universal Router Module for the IGX platform

cevChassisURM2FE  OBJECT IDENTIFIER
    ::= { cevChassis 241 }

-- Universal router module with 2 Fast Ethernet interfaces for IGX platform

cevChassisURM2FE2V  OBJECT IDENTIFIER
    ::= { cevChassis 242 }

-- Universal Router Module, with 2 Fast Ethernet ports, and 2 digital voice ports (T1 or E1)

cevChassisCAP340  OBJECT IDENTIFIER
    ::= { cevChassis 245 }

-- Aironet Wireless LAN Access Point 340 series

cevChassisDPA7610  OBJECT IDENTIFIER
    ::= { cevChassis 247 }

-- The Cisco Digital PBX Adapter (DPA) enables the integration of Cisco Call Manager with Octel voice mail systems

cevChassis828  OBJECT IDENTIFIER
    ::= { cevChassis 248 }

-- Cisco 800 platform with 1 Ethernet, 1 G.991.2 (G.shdsl) Interface, data only model

cevChassisSOHO78  OBJECT IDENTIFIER
    ::= { cevChassis 249 }

-- SOHO (Small Office Home Office) G.SHDSL Router, 1 Ethernet and 1 G.991.2 (G.shdsl) Interface, data only model

cevChassis806  OBJECT IDENTIFIER
    ::= { cevChassis 250 }

-- Cisco SOHO (Small Office Home Office) router with 4 hubbed 10BaseT Ethernet LAN interfaces and 1 10BaseT Ethernet WAN interface

cevChassis12416  OBJECT IDENTIFIER
    ::= { cevChassis 251 }

-- Cisco 12000 platform with 16 slots and 10G Fabric card

cevChassisCat2948gL3Dc  OBJECT IDENTIFIER
    ::= { cevChassis 252 }

-- A fixed-configuration Layer 3 Ethernet switch featuring IP, IPX, and IP mulitcast with 48 10/100BaseTX ports and 2 GBIC Gigabit ports using DC power

cevChassisCat4908gL3Dc  OBJECT IDENTIFIER
    ::= { cevChassis 253 }

-- A fixed-configuration L3 Ethernet switch featuring IP,IPX and IP multicast with 8 GBIC ports using DC power

cevChassis12406  OBJECT IDENTIFIER
    ::= { cevChassis 254 }

-- Cisco 12400 platform with 6 slots

cevChassisPIXFirewall506  OBJECT IDENTIFIER
    ::= { cevChassis 255 }

-- Cisco PIX Firewall 506

cevChassisPIXFirewall515  OBJECT IDENTIFIER
    ::= { cevChassis 256 }

-- Cisco PIX Firewall 515

cevChassisPIXFirewall520  OBJECT IDENTIFIER
    ::= { cevChassis 257 }

-- Cisco PIX Firewall 520

cevChassisPIXFirewall525  OBJECT IDENTIFIER
    ::= { cevChassis 258 }

-- Cisco PIX Firewall 525

cevChassisPIXFirewall535  OBJECT IDENTIFIER
    ::= { cevChassis 259 }

-- Cisco PIX Firewall 535

cevChassis12410  OBJECT IDENTIFIER
    ::= { cevChassis 260 }

-- Cisco 12410 platform with 10 slots

cevChassis811  OBJECT IDENTIFIER
    ::= { cevChassis 261 }

-- ISDN router for Japan with 1 10BaseT Ethernet port, 1 ISDN BRI(Basic Rate Interface) U, integrated DSU(Data Service Unit)

cevChassis813  OBJECT IDENTIFIER
    ::= { cevChassis 262 }

-- ISDN router for Japan with 10 BaseT 4 ports hub , 1 ISDN BRI(Basic Rate Interface) U, integrated DSU(Data Service Unit) and 2 RJ-11

cevChassis10720  OBJECT IDENTIFIER
    ::= { cevChassis 263 }

-- IP + Optical Access Router

cevChassisMWR1900  OBJECT IDENTIFIER
    ::= { cevChassis 264 }

-- The Mobile Wireless router is a router targeted at application in a cell site Base Transciever Station (BTS) providing T1/E1 backhaul connections to the aggregation node in Radio Access Networks (RAN)

cevChassis4224  OBJECT IDENTIFIER
    ::= { cevChassis 265 }

-- A standalone  24 port powered Ethernet switch, router and voice gateway

cevChassisWSC6513  OBJECT IDENTIFIER
    ::= { cevChassis 266 }

-- Catalyst 6000 series chassis with 13 slots

cevChassisCisco7603  OBJECT IDENTIFIER
    ::= { cevChassis 267 }

-- Cisco Internet Router 7600 Series Chassis with 3 slots

cevChassisCisco7606  OBJECT IDENTIFIER
    ::= { cevChassis 268 }

-- Cisco Internet Router 7600 Series Chassis with 6 slots

cevChassis7401ASR  OBJECT IDENTIFIER
    ::= { cevChassis 269 }

-- Cisco 7400 platform, ASR series with 1 slot

cevChassis1105  OBJECT IDENTIFIER
    ::= { cevChassis 271 }

-- CiscoWorks network management chassis

cevChassisONS15540ESP  OBJECT IDENTIFIER
    ::= { cevChassis 272 }

-- Cisco ONS 15540 Extended Services Platform Chassis

cevChassisCe507  OBJECT IDENTIFIER
    ::= { cevChassis 275 }

-- Cisco Content Engine Model 507

cevChassisCe560  OBJECT IDENTIFIER
    ::= { cevChassis 276 }

-- Cisco Content Engine Model 560

cevChassisCe590  OBJECT IDENTIFIER
    ::= { cevChassis 277 }

-- Cisco Content Engine Model 590

cevChassisCe7320  OBJECT IDENTIFIER
    ::= { cevChassis 278 }

-- Cisco Content Engine Model 7320

cevChassis2691  OBJECT IDENTIFIER
    ::= { cevChassis 279 }

-- One Network Module slot, three WIC slot, two Fast Ethernet port MARS router

cevChassis3725  OBJECT IDENTIFIER
    ::= { cevChassis 280 }

-- Two Network Module slot, three WIC slot, two Fast Ethernet port MARS router

cevChassis1760  OBJECT IDENTIFIER
    ::= { cevChassis 282 }

-- Analog/digital voice capable, 19" rack-mount (1RU) Cisco 1700 platform with 2 WIC/VIC slots and 2 VIC-only slots

cevChassisPIXFirewall501  OBJECT IDENTIFIER
    ::= { cevChassis 283 }

-- Cisco PIX Firewall 501

cevChassis2610M  OBJECT IDENTIFIER
    ::= { cevChassis 284 }

-- c2600M chassis with 1 integrated ethernet interface

cevChassis2611M  OBJECT IDENTIFIER
    ::= { cevChassis 285 }

-- c2600M chassis with 2 integrated ethernet interfaces

cevChassis12404  OBJECT IDENTIFIER
    ::= { cevChassis 289 }

-- Cisco 12400 platform with 4 slots

cevChassis9004  OBJECT IDENTIFIER
    ::= { cevChassis 290 }

-- Cisco 9000 Chassis

cevChassisCat295012G  OBJECT IDENTIFIER
    ::= { cevChassis 293 }

-- Cisco Catalyst c2950 switch with 12 10/100 BaseTX port and 2 GBIC (Gigabit Interface Converter) slots (WS-c2950G-12)

cevChassisCat295024G  OBJECT IDENTIFIER
    ::= { cevChassis 294 }

-- Cisco Catalyst c2950 switch with 24 10/100 BaseTX ports and 2 GBIC (Gigabit Interface Converter) slots (WS-c2950G-24)

cevChassisCat295048G  OBJECT IDENTIFIER
    ::= { cevChassis 295 }

-- Cisco Catalyst c2950 switch with 48 10/100 BaseTX ports and 2 GBIC (Gigabit Interface Converter) slots (WS-c2950G-48)

cevChassisCat355012G  OBJECT IDENTIFIER
    ::= { cevChassis 297 }

-- 10 Gig (GBIC) + 2 10/100/1000baseT ports, fixed configuration layer 2/3 Ethernet switch

cevChassisCE507AV  OBJECT IDENTIFIER
    ::= { cevChassis 298 }

-- Cisco Content Engine Model 507-AV

cevChassisCE560AV  OBJECT IDENTIFIER
    ::= { cevChassis 299 }

-- Cisco Content Engine Model 560-AV

cevChassisIE2105  OBJECT IDENTIFIER
    ::= { cevChassis 300 }

-- The Cisco Intelligence Engine 2100 series is a new form of network device that provides intelligent network interface to applications and users

cevChassis3745  OBJECT IDENTIFIER
    ::= { cevChassis 301 }

-- 3700 family four slot modular router

cevChassis10005  OBJECT IDENTIFIER
    ::= { cevChassis 302 }

-- Cisco 10000 platform with 7 slots

cevChassis10008  OBJECT IDENTIFIER
    ::= { cevChassis 303 }

-- Cisco 10000 platform with 7 slots

cevChassis7304  OBJECT IDENTIFIER
    ::= { cevChassis 304 }

-- Cisco 7300 Chassis

cevChassis7505  OBJECT IDENTIFIER
    ::= { cevChassis 305 }

-- Cisco 7505 Chassis

cevChassis1721  OBJECT IDENTIFIER
    ::= { cevChassis 310 }

-- Enhanced 1720 with support for onboard Fast Ethernet and 2 WAN Interface cards and optional hardware encryption module

cevChassisCat4000Sup3  OBJECT IDENTIFIER
    ::= { cevChassis 311 }

-- Catalyst 4000 Supervisor III

cevChassis827H  OBJECT IDENTIFIER
    ::= { cevChassis 312 }

-- Cisco 800 platform with 4-port 10Base-T Ethernet, and 1 ADSL over POTS Interface, data only model

cevChassisSOHO77H  OBJECT IDENTIFIER
    ::= { cevChassis 313 }

-- SOHO (Small Office Home Office) Router, 4-port 10Base-T Ethernet, and 1 ADSL over POTS Interface, data only model

cevChassisCat4006  OBJECT IDENTIFIER
    ::= { cevChassis 314 }

-- Catalyst 4000 with 6 slots (WS-C4006)

cevChassisCat355024Mmf  OBJECT IDENTIFIER
    ::= { cevChassis 315 }

-- Catalyst 3550 24 10/100Mbps Multi Mode Fiber ports + 2 Gig uplinks fixed configuration Layer 2/Layer 3 Ethernet Switch

cevChassisWSC6503  OBJECT IDENTIFIER
    ::= { cevChassis 316 }

-- Catalyst 6000 series chassis with 3 slots

cevChassisPIXFirewall506E  OBJECT IDENTIFIER
    ::= { cevChassis 317 }

-- Cisco PIX Firewall 506E

cevChassisPIXFirewall515E  OBJECT IDENTIFIER
    ::= { cevChassis 318 }

-- Cisco PIX Firewall 515E

cevChassisCat355024Dc  OBJECT IDENTIFIER
    ::= { cevChassis 319 }

-- Catalyst 3550 10/100Base-Tx ports + 2 Gig uplinks fixed configuration Layer 2/Layer 3 Ethernet Switch with DC power

cevChassisCe2636  OBJECT IDENTIFIER
    ::= { cevChassis 320 }

-- Cisco Content Engine Module for 26xx and 36xx series platforms

cevChassisCeDw2636  OBJECT IDENTIFIER
    ::= { cevChassis 321 }

-- Double Wide Cisco Content Engine Module for 26xx and 36xx series

cevChassis14MGX8830  OBJECT IDENTIFIER
    ::= { cevChassis 323 }

-- Cisco Multiservice Gigabit Switch with 14 half height slots

cevChassisONS15530NEBS  OBJECT IDENTIFIER
    ::= { cevChassis 325 }

-- Cisco ONS 15530 Chassis, NEBS compliant

cevChassisONS15530ETSI  OBJECT IDENTIFIER
    ::= { cevChassis 326 }

-- Cisco ONS 15530 Chassis, ETSI compliant

cevChassisSOHO71  OBJECT IDENTIFIER
    ::= { cevChassis 327 }

-- Cisco SOHO Platform(Small Office Home Office) router having 10BaseT 4 ports hubed Ethernet LAN interface and 1 10BaseT Ethernet WAN Interface

cevChassis6400UAC  OBJECT IDENTIFIER
    ::= { cevChassis 328 }

-- Cisco 6400 Universal Access Concentrator

cevChassisRPMPR  OBJECT IDENTIFIER
    ::= { cevChassis 329 }

-- This is a chassis value for RPM-PR. RPM-PR is router blade in MGX series switch

cevChassis2610XM  OBJECT IDENTIFIER
    ::= { cevChassis 330 }

-- Cisco 2610XM platform with 1 integrated fast ethernet interfaces with SDRAM

cevChassis2611XM  OBJECT IDENTIFIER
    ::= { cevChassis 331 }

-- Cisco 2611XM platform with 2 integrated fast ethernet interfaces with SDRAM

cevChassis2620XM  OBJECT IDENTIFIER
    ::= { cevChassis 332 }

-- Cisco 2620XM platform with 1 integrated fast ethernet interfaces with SDRAM

cevChassis2621XM  OBJECT IDENTIFIER
    ::= { cevChassis 333 }

-- Cisco 2621XM platform with 2 integrated fast ethernet interfaces with SDRAM

cevChassis2650XM  OBJECT IDENTIFIER
    ::= { cevChassis 334 }

-- Cisco 2650XM platform with 1 integrated fast ethernet interfaces with SDRAM

cevChassis2651XM  OBJECT IDENTIFIER
    ::= { cevChassis 335 }

-- Cisco 2651XM platform with 2 integrated fast ethernet interfaces with SDRAM

cevChassisCat295024GDc  OBJECT IDENTIFIER
    ::= { cevChassis 336 }

-- Cisco Catalyst c2950 switch with 24 10/100 BaseTX ports and 2 GBIC (Gigabit Interface Converter) slots and DC power(WS-c2950G-24-DC)

cevChassisONS15540ESPx  OBJECT IDENTIFIER
    ::= { cevChassis 337 }

-- Cisco ONS 15540 Extended Services Platform chassis (without optical backplane)

cevChassisC7301  OBJECT IDENTIFIER
    ::= { cevChassis 340 }

-- Cisco 7300 platform, 1 Rack Unit (RU) application specific router with 1 slot

cevChassis12816  OBJECT IDENTIFIER
    ::= { cevChassis 341 }

-- Cisco 12816 platform with 16 slots

cevChassis12810  OBJECT IDENTIFIER
    ::= { cevChassis 342 }

-- Cisco 12810 platform with 10 slots

cevChassisCat295024sx  OBJECT IDENTIFIER
    ::= { cevChassis 347 }

-- Cisco Catalyst c2950 switch with 24 10/100 BaseTX ports and 2 fixed 1000Base Multimode fiber (SX) ports (WS-C2950SX-24)

cevChassisAs5400HPX  OBJECT IDENTIFIER
    ::= { cevChassis 348 }

-- chassis for cisco As5400HPX

cevChassisAs5350HPX  OBJECT IDENTIFIER
    ::= { cevChassis 349 }

-- chassis for cisco AS5350HPX

cevChassisCat2955T12  OBJECT IDENTIFIER
    ::= { cevChassis 350 }

-- Cisco Catalyst c2955 Industrial switch with 12 10/100 BaseTX ports and 2 10/100/1000 Base-TX ports

cevChassisCat2955C12  OBJECT IDENTIFIER
    ::= { cevChassis 351 }

-- Cisco Catalyst c2955 Industrial switch with 12 10/100 Base TX ports and 2 100 Base-FX ports

cevChassis837  OBJECT IDENTIFIER
    ::= { cevChassis 354 }

-- Cisco 837 platform with 4-port 10/100 Base-T Ethernet Switch, 1 ADSL over POTS interface, data only model, hardware encryption

cevChassisSOHO97  OBJECT IDENTIFIER
    ::= { cevChassis 355 }

-- SOHO (Small Office Home Office) Router, with 4-port 10/100 Base-T Ethernet Switch, 1 ADSL over POTS interface, data only model

cevChassis831  OBJECT IDENTIFIER
    ::= { cevChassis 356 }

-- Cisco 831 platform with 4-port 10/100 Base-T Ethernet Switch, 1 10Base-T Ethernet WAN interface, hardware encryption

cevChassisSOHO91  OBJECT IDENTIFIER
    ::= { cevChassis 357 }

-- SOHO (Small Office Home Office) Router, with 4-port 10/100 Base-T Ethernet Switch, 1 10Base-T Ethernet WAN interface

cevChassis836  OBJECT IDENTIFIER
    ::= { cevChassis 358 }

-- Cisco 836 platform with 4-port 10/100 Base-T Ethernet Switch, 1 ADSL over ISDN interface, 1 ISDN BRI S/T interface, hardware encryption

cevChassisSOHO96  OBJECT IDENTIFIER
    ::= { cevChassis 359 }

-- SOHO (Small Office Home Office) Router, with 4-port 10/100 Base-T Ethernet Switch, 1 ADSL over ISDN interface, 1 ISDN BRI S/T interface

cevChassisCat4507  OBJECT IDENTIFIER
    ::= { cevChassis 360 }

-- Catalyst 4000 with 7 slots with redundant supervisors ( WS-C4507 )

cevChassisCat4506  OBJECT IDENTIFIER
    ::= { cevChassis 361 }

-- Catalyst 4000 with 6 slots ( WS-C4506 )

cevChassisCat4503  OBJECT IDENTIFIER
    ::= { cevChassis 362 }

-- Catalyst 4000 with 3 slots ( WS-C4503 )

cevChassis7507  OBJECT IDENTIFIER
    ::= { cevChassis 363 }

-- Cisco 7507 chassis with 7 slots

cevChassis7513  OBJECT IDENTIFIER
    ::= { cevChassis 364 }

-- Cisco 7513 chassis with  13 slots

cevChassisAIRAP1100  OBJECT IDENTIFIER
    ::= { cevChassis 365 }

-- 1100 series WLAN Access Point with 1 10/100TX port, 1 IEEE 802.11 radio port

cevChassisCat2955S12  OBJECT IDENTIFIER
    ::= { cevChassis 367 }

-- Cisco Catalyst c2955 Industrial switch with 12 10/100 Base T ports and 2 100 Base-LX Single Mode Uplink ports

cevChassisCisco7609  OBJECT IDENTIFIER
    ::= { cevChassis 368 }

-- 9 slots chassis in Cisco 7600 family

cevChassisWSC65509  OBJECT IDENTIFIER
    ::= { cevChassis 369 }

-- 9 slots chassis in Catalyst 6500 family

cevChassisCat375024  OBJECT IDENTIFIER
    ::= { cevChassis 370 }

-- Catalyst 3750 24 10/100 ports + 2 Gigabit SFP ports fixed configuration Layer 2/Layer 3 Ethernet Stackable Switch. (SFP Small Formfactor Pluggable)

cevChassisCat375048  OBJECT IDENTIFIER
    ::= { cevChassis 371 }

-- Catalyst 3750 48 10/100 ports + 4 Gigabit SFP ports fixed configuration Layer 2/Layer 3 Ethernet Stackable Switch. (SFP Small Formfactor Pluggable)

cevChassisCat375024TS  OBJECT IDENTIFIER
    ::= { cevChassis 372 }

-- Catalyst 3750 24 10/100/1000 ports + 4 Gigabit SFP ports fixed configuration Layer 2/Layer 3 Ethernet Stackable Switch. (SFP Small Formfactor Pluggable)

cevChassisCat375024T  OBJECT IDENTIFIER
    ::= { cevChassis 373 }

-- Catalyst 3750 24 10/100/1000 ports fixed configuration Layer 2/Layer 3 Ethernet Stackable Switch.

cevChassisMWR1941DC  OBJECT IDENTIFIER
    ::= { cevChassis 374 }

-- The Mobile Wireless Router (MWR-1941-DC) is a router with a universal power supply targeted at application in a cell site Base Transceiver Station (BTS) providing T1/E1 backhaul connections to the aggregation node in Radio Access Networks (RAN).

cevChassisDSC9506  OBJECT IDENTIFIER
    ::= { cevChassis 375 }

-- DS-C9506  - MDS 9506 Chassis

cevChassisDSC9509  OBJECT IDENTIFIER
    ::= { cevChassis 376 }

-- DS-C9509  - MDS 9509 Chassis

cevChassisDSC9513  OBJECT IDENTIFIER
    ::= { cevChassis 377 }

-- DS-C9513  - MDS 9513 Chassis

cevChassisONS15201  OBJECT IDENTIFIER
    ::= { cevChassis 378 }

-- Cisco ONS 15201 Single Channel Unit

cevChassisONS15252  OBJECT IDENTIFIER
    ::= { cevChassis 379 }

-- Cisco ONS 15252 Multi Channel Unit

cevChassisMdsDSX9216  OBJECT IDENTIFIER
    ::= { cevChassis 380 }

-- DS-X9216  - MDS 9216 Chassis

cevChassisVG200  OBJECT IDENTIFIER
    ::= { cevChassis 381 }

-- The Cisco VG200 chassis for Voice-over-IP (VoIP) Gateway

cevChassisAIRAP1210  OBJECT IDENTIFIER
    ::= { cevChassis 382 }

-- 1200 series WLAN Access Point on Cisco IOS platform with 1 10/100TX port, 1 CardBus slot, 1 Mini PCI slot

cevChassisCat375048PS  OBJECT IDENTIFIER
    ::= { cevChassis 383 }

-- Catalyst 3750 48 10/100 ports with In-Line Power + 2 Gigabit SFP ports fixed configuration Layer 2/Layer 3 Ethernet Stackable Switch.(SFP Small Formfactor Pluggable)

cevChassisCat375024PS  OBJECT IDENTIFIER
    ::= { cevChassis 384 }

-- Catalyst 3750 24 10/100 ports with In-Line Power + 2 Gigabit SFP ports fixed configuration Layer 2/Layer 3 Ethernet Stackable Switch.(SFP Small Formfactor Pluggable)

cevChassisCe510  OBJECT IDENTIFIER
    ::= { cevChassis 385 }

-- Cisco Content Engine Model 510

cevChassisCe565  OBJECT IDENTIFIER
    ::= { cevChassis 386 }

-- Cisco Content Engine Model 565

cevChassisCe7305  OBJECT IDENTIFIER
    ::= { cevChassis 387 }

-- Cisco Content Engine Model 7305

cevChassisCe7325  OBJECT IDENTIFIER
    ::= { cevChassis 388 }

-- Cisco Content Engine Model 7325

cevChassisCe4630  OBJECT IDENTIFIER
    ::= { cevChassis 389 }

-- Cisco Content Engine Model 4630

cevChassisCe4650  OBJECT IDENTIFIER
    ::= { cevChassis 390 }

-- Cisco Content Engine Model 4650

cevChassisCat297024  OBJECT IDENTIFIER
    ::= { cevChassis 391 }

-- Catalyst 2970 24 10/100/1000 ports fixed configuration Layer 2 Ethernet Switch

cevChassisCisco7613  OBJECT IDENTIFIER
    ::= { cevChassis 392 }

-- Cisco Internet router 7600 Series Chassis with 13 slots

cevChassisCat3750Ge12Sfp  OBJECT IDENTIFIER
    ::= { cevChassis 394 }

-- Catalyst 3750 12 Ethernet Gigabit SFP ports stackable switch.(SFP: Small Form factor Pluggable)

cevChassisCr4450  OBJECT IDENTIFIER
    ::= { cevChassis 395 }

-- Cisco Content Router Model 4450

cevChassisAIRBR1410  OBJECT IDENTIFIER
    ::= { cevChassis 396 }

-- 1410 Series Wireless LAN Bridge on Cisco IOS platform with 1 10/100Tx port and 1 5-GHz radio

cevChassisWSC6509neba  OBJECT IDENTIFIER
    ::= { cevChassis 397 }

-- Catalyst 6500 series chassis with 9 slots

cevChassisCat4510  OBJECT IDENTIFIER
    ::= { cevChassis 398 }

-- Catalyst 4000 with 10 slots ( WS-C4510R )

cevChassisCisco1711  OBJECT IDENTIFIER
    ::= { cevChassis 399 }

-- Enhanced security router with 4 FastEthernet switch ports, 1 Analog modem port, 1 FastEthernet port and a hardware encryption module

cevChassisCisco1712  OBJECT IDENTIFIER
    ::= { cevChassis 400 }

-- Enhanced security router with 4 FastEthernet switch ports, 1 Basic Rate Interface(S/T)  data port, 1 FastEthernet port and a hardware encryption module.

cevChassisCisco1701  OBJECT IDENTIFIER
    ::= { cevChassis 401 }

-- c1701 is a re-packaging of existing products to create a fixed configuration sku. It has ADSLoPOTs WIC and ISDN BRI (S/T) WIC riveted into it.

cevChassis29408TT  OBJECT IDENTIFIER
    ::= { cevChassis 402 }

-- Catalyst 2940 L2 switch with 8 10/100 copper ports and 1 10/100/1000 copper uplink port.

cevChassis29408TF  OBJECT IDENTIFIER
    ::= { cevChassis 403 }

-- Catalyst 2940 L2 switch with 8 10/100 copper ports, 1 100 FX Uplink port and 1 Gigabit SFP Module slot.

cevChassis3825  OBJECT IDENTIFIER
    ::= { cevChassis 404 }

-- Two Network Module Slots, Four WIC slots, Two Gigabit Ethernet ports 3800 family router

cevChassis3845  OBJECT IDENTIFIER
    ::= { cevChassis 405 }

-- Four Network Module Slots, Four WIC slots, Two Gigabit Ethernet ports 3800 family router

cevChassis2430Iad24Fxs  OBJECT IDENTIFIER
    ::= { cevChassis 406 }

-- cIAD2430 with 24FXS, 2FE

cevChassis2431Iad8Fxs  OBJECT IDENTIFIER
    ::= { cevChassis 407 }

-- cIAD2431 with 8FXS, 2FE, 1T1/E1, 1 vwic slot

cevChassis2431Iad16Fxs  OBJECT IDENTIFIER
    ::= { cevChassis 408 }

-- cIAD2431 with 16FXS, 2FE, 1T1/E1, 1 vwic slot

cevChassis2431Iad1T1E1  OBJECT IDENTIFIER
    ::= { cevChassis 409 }

-- cIAD2431 with 2FE, 2T1/E1, 1 vwic slot

cevChassis2432Iad24Fxs  OBJECT IDENTIFIER
    ::= { cevChassis 410 }

-- cIAD2432 with 24FXS, 2FE, 2T1E1, 1 vwic slot

cevChassisDSC9140K9  OBJECT IDENTIFIER
    ::= { cevChassis 411 }

-- DS-C9140-K9 - MDS 9140, 40-Port Fixed config Fabric Switch Chassis

cevChassisAirAp350IOS  OBJECT IDENTIFIER
    ::= { cevChassis 412 }

-- Cisco Wireless LAN Access Point 350 series on IOS platform with 1 10/100TX port, 1 IEEE 802.11 radio port

cevChassis3220  OBJECT IDENTIFIER
    ::= { cevChassis 413 }

-- Cisco 3220 Platform - Mobile Access Router Chassis.

cevChassisDSC9120K9  OBJECT IDENTIFIER
    ::= { cevChassis 414 }

-- DS-C9120-K9 - MDS 9120, 20-Port Fixed config Fabric Switch Chassis

cevChassisCat295024LreSt997  OBJECT IDENTIFIER
    ::= { cevChassis 415 }

-- Cisco Catalyst2950 Long Reach Ethernet switch that confirms to ETSI 997 with 24 LRE interfaces, 2 10/100/1000 Small form factor copper interfaces and DC power supply(WS-C2905ST-24-LRE-997)

cevChassisCat6kSup720  OBJECT IDENTIFIER
    ::= { cevChassis 416 }

-- Catalyst 6500 Supervisor Module 720 CPU board that is treated as a standalone system by the NMS

cevChassisVG224  OBJECT IDENTIFIER
    ::= { cevChassis 417 }

-- Line side Analog Gateway with 24FXS Analog ports

cevChassisCat295048T  OBJECT IDENTIFIER
    ::= { cevChassis 418 }

-- Cisco Catalyst c2950 switch with 48 10/100BaseT ports and 2 10/100/1000 BaseT ports

cevChassisCat295048SX  OBJECT IDENTIFIER
    ::= { cevChassis 419 }

-- Cisco Catalyst c2950 switch with 48 10/100BaseTX ports and 2 fixed 1000Base Multimode fiber (SX) ports

cevChassisCat297024TS  OBJECT IDENTIFIER
    ::= { cevChassis 420 }

-- Catalyst 2970 24 10/100/1000 ports + 4 Gigabit SFP ports fixed configuration Layer 2 Ethernet Switch.

cevChassisCrs116Fabric  OBJECT IDENTIFIER
    ::= { cevChassis 421 }

-- CRS1 16 slots Fabric Chassis

cevChassisCrs116LineCard  OBJECT IDENTIFIER
    ::= { cevChassis 422 }

-- CRS1 16 slots Line Card Chassis

cevChassisCrs18LineCard  OBJECT IDENTIFIER
    ::= { cevChassis 423 }

-- CRS1 8 slots Line Card Chassis

cevChassisCat356048PS  OBJECT IDENTIFIER
    ::= { cevChassis 424 }

-- Catalyst 3560 48 10/100 ports with In-Line Power + 4 Gigabit SFP ports fixed configuration Layer 2/Layer 3 Ethernet Switch.(SFP Small Formfactor Pluggable)

cevChassisCat356024PS  OBJECT IDENTIFIER
    ::= { cevChassis 425 }

-- Catalyst 3560 24 10/100 ports with In-Line Power + 2 Gigabit SFP ports fixed configuration Layer 2/Layer 3 Ethernet Switch.(SFP Small Formfactor Pluggable)

cevChassisAIRBR1300  OBJECT IDENTIFIER
    ::= { cevChassis 426 }

-- Cisco Aironet 1300 Series Wireless Bridge with 1 10/100TX Ethernet port, 1 IEEE 802.11g radio port

cevChassis12004  OBJECT IDENTIFIER
    ::= { cevChassis 427 }

-- Cisco 12000 platform with 4 slots

cevChassis12006  OBJECT IDENTIFIER
    ::= { cevChassis 428 }

-- Cisco 12000 platform with 6 slots

cevChassis851  OBJECT IDENTIFIER
    ::= { cevChassis 429 }

-- Cisco 851 platform with 1 10/100T ethernet WAN interface, 4-port 10/100 Base-T LAN Ethernet switch, 4 USB ports, hardware encryption and Wireless LAN card

cevChassis857  OBJECT IDENTIFIER
    ::= { cevChassis 430 }

-- Cisco 857 platform with 1 DSL over POTS WAN interface, 4-port 10/100 Base-T LAN Ethernet switch, 4 USB ports, hardware encryption and an optional Wireless LAN card

cevChassis876  OBJECT IDENTIFIER
    ::= { cevChassis 431 }

-- Cisco 876 platform with 1 ADSL over ISDN WAN interface, 4-port 10/100 Base-T LAN Ethernet switch, 4 USB ports, 1 ISDN BRI S/T interface, hardware encryption and an optional Wireless LAN card

cevChassis877  OBJECT IDENTIFIER
    ::= { cevChassis 432 }

-- Cisco 877 platform with 1 ADSL over POTS WAN interface, 4-port 10/100 BASE-T LAN Ethernet switch, 4 USB ports, hardware encryption and an optional Wireless LAN card

cevChassis878  OBJECT IDENTIFIER
    ::= { cevChassis 433 }

-- Cisco 878 platform with 1 SHDSL WAN interface, 4-port 10/100 Base-T LAN Ethernet switch, 4 USB ports, 1 ISDN BRI S/T interface, hardware encryption and an optional Wireless LAN card

cevChassis871  OBJECT IDENTIFIER
    ::= { cevChassis 434 }

-- Cisco 871 platform with 1 10/100T ethernet WAN interface, 4-port 10/100 Base-T LAN Ethernet switch, 4 USB ports, hardware encryption and an optional Wireless LAN card

cevChassisUmg9820  OBJECT IDENTIFIER
    ::= { cevChassis 435 }

-- A stand-alone "pizza-box" video QAM device enabling delivery of VOD/SVOD/NVPR services via low-cost, line-rate GbE transport solutions from centralized servers to local cable hubs

cevChassis2811  OBJECT IDENTIFIER
    ::= { cevChassis 436 }

-- 2800 Family Router with two integrated fast ethernets and integrated VPN

cevChassis2821  OBJECT IDENTIFIER
    ::= { cevChassis 437 }

-- 2800 Family Router with two integrated gigabit ethernets and integrated VPN

cevChassis2851  OBJECT IDENTIFIER
    ::= { cevChassis 438 }

-- 2800 Family Router with two integrated gigabit ethernets and integrated VPN

cevChassisCat375024ME  OBJECT IDENTIFIER
    ::= { cevChassis 439 }

-- Metro Ethernet Catalyst  3750 24-10/100 + 2 SFP ports for downlinks and 2 SFP ES (Enhanched Service) ports for uplinks
-- Assignment Cancelled. Reuse the OID  cevChassisWGB3201      OBJECT IDENTIFIER ::= { cevChassis 440 }    Cisco 3201 802.11g Work Group Bridge Wireless MIC (Mobile Interface card) with 802.11g wireless interface in the PC104 + form factor. An interface card for the existing MAR 3200 products(Mobile Access Router)
-- Assignment Cancelled. Reuse the OID  cevChassisAP3201      OBJECT IDENTIFIER ::= { cevChassis 441 }    Cisco 3201 Wireless MIC (Mobile Interface card) Root Access Point card with 802.11g wireless interface in the PC104 + form factor. An interface card for the existing MAR 3200 products (Mobile Access Router)

cevChassisMdsDSC9216AK9  OBJECT IDENTIFIER
    ::= { cevChassis 442 }

-- DS-C9216A-K9 - MDS 9216A Chassis

cevChassis3201WMIC  OBJECT IDENTIFIER
    ::= { cevChassis 443 }

-- Cisco 3201 Wireless MIC (Mobile Interface card) with 802.11g wireless interface in the PC104+ form factor. An interface card for the existing MAR 3200 products(Mobile Access Router)

cevChassisCat3750G16TD  OBJECT IDENTIFIER
    ::= { cevChassis 444 }

-- Cisco Catalyst 3750 switch with 16 gigabit and one 10G ethernet port (WS-C3750G-16TD)

cevChassis1718  OBJECT IDENTIFIER
    ::= { cevChassis 445 }

-- Voice capable Cisco 1700 Router with 4 FastEthernet switch ports, 1 FastEthernet port and 4 FXS-DID ports

cevChassisIGESM  OBJECT IDENTIFIER
    ::= { cevChassis 446 }

-- Cisco Systems Intelligent Gigabit Ethernet Switch Module for IBM eServer BladeCenter (OS-CIGESM-18TT-E)

cevChassisASA5510  OBJECT IDENTIFIER
    ::= { cevChassis 447 }

-- This is Adaptive Security Appliance (ASA) 5510. This security appliance combines functions of firewall, intrusion prevention, VPN hub and remote access hub. This is a standalone appliance with no linecards

cevChassisASA5520  OBJECT IDENTIFIER
    ::= { cevChassis 448 }

-- This is Adaptive Security Appliance (ASA) 5520. This security appliance combines functions of firewall, IDS sensor, VPN hub and remote access hub. This is a modular chassis with a slot for one line card

cevChassisASA5540  OBJECT IDENTIFIER
    ::= { cevChassis 449 }

-- This is Adaptive Security Appliance (ASA) 5540. This security appliance combines functions of firewall, intrusion prevention, VPN hub and remote access hub. This is a modular chassis with a slot for one line card

cevChassis1841  OBJECT IDENTIFIER
    ::= { cevChassis 450 }

-- 1700 Next Generation data only router with 2 slots

cevChassis2801  OBJECT IDENTIFIER
    ::= { cevChassis 451 }

-- 1700 Next Generation voice enabled router with 4 slots

cevChassisCe511K9  OBJECT IDENTIFIER
    ::= { cevChassis 452 }

-- Cisco Content Engine Model   CE-511-K9

cevChassisCe566K9  OBJECT IDENTIFIER
    ::= { cevChassis 453 }

-- Cisco Content Engine Model   CE-566-K9

cevChassisASA5560  OBJECT IDENTIFIER
    ::= { cevChassis 454 }

-- This is the Service Provider class Adaptive Security Appliance(ASA) model 5560. This security appliance combines functions of firewall, IDS sensor, VPN hub and remote access hub and provides for redundant Security Services cards and power supply units

cevChassisMGX8880  OBJECT IDENTIFIER
    ::= { cevChassis 455 }

-- Cisco MGX8880 chassis with 32 half height slots

cevChassisCe7306K9  OBJECT IDENTIFIER
    ::= { cevChassis 456 }

-- Cisco Content Engine Model   CE-7306-K9

cevChassisCe7326K9  OBJECT IDENTIFIER
    ::= { cevChassis 457 }

-- Cisco Content Engine Model   CE-7326-K9

cevChassisCat3750G24PS  OBJECT IDENTIFIER
    ::= { cevChassis 458 }

-- Catalyst 3750 24 10/100/1000 Power over Ethernet ports + 4 Gigabit SFP ports fixed configuration Layer 2/Layer 3 Ethernet Stackable Switch. (SFP Small Formfactor Pluggable)

cevChassisCat3750G48PS  OBJECT IDENTIFIER
    ::= { cevChassis 459 }

-- Catalyst 3750 48 10/100/1000 Power over Ethernet ports + 4 Gigabit SFP ports fixed configuration Layer 2/Layer 3 Ethernet Stackable Switch. (SFP Small Formfactor Pluggable)

cevChassisCat3750G48TS  OBJECT IDENTIFIER
    ::= { cevChassis 460 }

-- Catalyst 3750 48 10/100/1000 ports + 4 Gigabit SFP ports fixed configuration Layer 2/Layer 3 Ethernet Stackable Switch. (SFP Small Formfactor Pluggable)

cevChassisCat297048TS  OBJECT IDENTIFIER
    ::= { cevChassis 461 }

-- Catalyst 2970 48 10/100/1000 ports + 4 Gigabit SFP ports fixed configuration Layer 2 Ethernet Switch. (SFP Small Form factor Pluggable)

cevChassisDSX9132K9  OBJECT IDENTIFIER
    ::= { cevChassis 462 }

-- DS-X9132-K9 MDS 9132 Chassis

cevChassisDSX9116K9  OBJECT IDENTIFIER
    ::= { cevChassis 463 }

-- DS-X9116-K9 MDS 9116 Chassis

cevChassisBMGX8830  OBJECT IDENTIFIER
    ::= { cevChassis 464 }

-- Cisco Multiservice Switch (Model B) with 14 half height slots

cevChassisBMGX8850  OBJECT IDENTIFIER
    ::= { cevChassis 465 }

-- Cisco Multiservice Gigabit Switch (Model B) with 32 half height slots

cevChassisWsC4948  OBJECT IDENTIFIER
    ::= { cevChassis 466 }

-- Cisco Catalyst 4000 series fixed configuration switch with 48 wirespeed 10/100/1000BaseT ports and 4 wirespeed 1000BaseX SFP ports

cevChassisCe501K9  OBJECT IDENTIFIER
    ::= { cevChassis 467 }

-- Cisco Content Engine Model   CE-501-K9

cevChassisCat3560G24PS  OBJECT IDENTIFIER
    ::= { cevChassis 468 }

-- Catalyst 3560 24 10/100/1000 Power over Ethernet ports + 4 Gigabit SFP ports fixed configuration Layer 2/Layer 3 Ethernet Switch. (SFP Small Formfactor Pluggable)

cevChassisCat3560G24TS  OBJECT IDENTIFIER
    ::= { cevChassis 469 }

-- Catalyst 3560 24 10/100/1000 ports + 4 Gigabit SFP ports fixed configuration Layer 2/Layer 3 Ethernet Switch. (SFP Small Formfactor Pluggable)

cevChassisCat3560G48PS  OBJECT IDENTIFIER
    ::= { cevChassis 470 }

-- Catalyst 3560 48 10/100/1000 Power over Ethernet ports + 4 Gigabit SFP ports fixed configuration Layer 2/Layer 3 Ethernet Switch. (SFP Small Formfactor Pluggable)

cevChassisCat3560G48TS  OBJECT IDENTIFIER
    ::= { cevChassis 471 }

-- Catalyst 3560 48 10/100/1000 ports + 4 Gigabit SFP ports fixed configuration Layer 2/Layer 3 Ethernet Switch. (SFP Small Formfactor Pluggable)

cevChassisDSC9216iK9  OBJECT IDENTIFIER
    ::= { cevChassis 472 }

-- 2-Slot MDS fabric switch chassis

cevChassisAs5400XM  OBJECT IDENTIFIER
    ::= { cevChassis 473 }

-- Chassis for Cisco AS5400XM

cevChassisAs5350XM  OBJECT IDENTIFIER
    ::= { cevChassis 474 }

-- Chassis for Cisco AS5350XM

cevChassisAIRAP1130  OBJECT IDENTIFIER
    ::= { cevChassis 475 }

-- Cisco Aironet 1130 series WLAN Access Point with 1 10/100TX port, dual IEEE 802.11a and 802.11g  radio port

cevChassisCisco7604  OBJECT IDENTIFIER
    ::= { cevChassis 476 }

-- Cisco 7604 chassis, a 4-slot chassis.

cevChassisWsC494810GE  OBJECT IDENTIFIER
    ::= { cevChassis 477 }

-- Catalyst 4000 series fixed configuration switch with 48 10/100/1000BaseT wirespeed ports and two 10Gbps ports

cevChassisCat3750G24TS1U  OBJECT IDENTIFIER
    ::= { cevChassis 478 }

-- Catalyst 3750 24 10/100/1000 Ethernet ports + 4 Gigabit SFP ports fixed configuration Layer 2/Layer 3 Ethernet Stackable Switch. (SFP Small Formfactor Pluggable)
-- removed can reuse assignment

cevChassis371098HP001  OBJECT IDENTIFIER
    ::= { cevChassis 480 }

-- 24 port Gigabit Ethernet switch module for HP ProLiant BL p-class server chassis

cevChassisSB101  OBJECT IDENTIFIER
    ::= { cevChassis 481 }

-- (Small Buisness) Router, with 4-port 10/100 Base-T Ethernet Switch, 1 10Base-T Ethernet WAN interface

cevChassisSB106  OBJECT IDENTIFIER
    ::= { cevChassis 482 }

-- (Small Buisness) Router, with 4-port 10/100 Base-T Ethernet Switch, 1 ADSL over ISDN interface, 1 ISDN BRI S/T interface

cevChassisSB107  OBJECT IDENTIFIER
    ::= { cevChassis 483 }

-- (Small Buisness) Router, with 4-port 10/100 Base-T Ethernet Switch, 1 ADSL over POTS interface, data only model

cevChassisCat356024TS  OBJECT IDENTIFIER
    ::= { cevChassis 484 }

-- Catalyst 3560 24 10/100 ports + 2 Gigabit SFP ports fixed configuration Layer 2/Layer 3 Ethernet Switch. (SFP Small Formfactor Pluggable)

cevChassisCat356048TS  OBJECT IDENTIFIER
    ::= { cevChassis 485 }

-- Catalyst 3560 48 10/100 ports + 4 Gigabit SFP ports fixed configuration Layer 2/Layer 3 Ethernet Switch. (SFP Small Formfactor Pluggable)

cevChassisONS15310  OBJECT IDENTIFIER
    ::= { cevChassis 486 }

-- Cisco ONS 15310 Platform Chassis

cevChassis1801  OBJECT IDENTIFIER
    ::= { cevChassis 487 }

-- Cisco 1800 platform with 1 ADSL over POTS WAN interface, 8-port 10/100 BASE-T LAN Ethernet switch, 1 ISDN BRI S/T interface, 2 USB ports and an optional Wireless LAN card.

cevChassis1802  OBJECT IDENTIFIER
    ::= { cevChassis 488 }

-- Cisco 1800 platform with 1 ADSL over ISDN WAN interface, 8-port 10/100 BASE-T LAN Ethernet switch, 1 ISDN BRI S/T interface, 2 USB ports and an optional Wireless LAN card.

cevChassis1803  OBJECT IDENTIFIER
    ::= { cevChassis 489 }

-- Cisco 1800 platform with 1 G.SHDSL 4-wire interface, 8-port 10/100 BASE-T LAN Ethernet switch, 1 ISDN BRI S/T interface, 2 USB ports and an optional Wireless LAN card.

cevChassis1811  OBJECT IDENTIFIER
    ::= { cevChassis 490 }

-- Cisco 1800 platform with V.92 Modem, 8-port 10/100 BASE-T LAN Ethernet switch, 2 USB ports and an optional Wireless LAN card.

cevChassis1812  OBJECT IDENTIFIER
    ::= { cevChassis 491 }

-- Cisco 1800 platform with ISDN BRI S/T interface, 8-port 10/100 BASE-T LAN Ethernet switch, 2 USB ports and an optional Wireless LAN card.

cevWLSEChassis1130  OBJECT IDENTIFIER
    ::= { cevChassis 492 }

-- Chassis for Cisco WLSE 1130.

cevWLSEChassis1030  OBJECT IDENTIFIER
    ::= { cevChassis 493 }

-- Chassis for Cisco WLSE Express 1030.

cevChassisIDS4210  OBJECT IDENTIFIER
    ::= { cevChassis 495 }

-- Cisco Intrusion Detection System 4210

cevChassisIDS4215  OBJECT IDENTIFIER
    ::= { cevChassis 496 }

-- Cisco Intrusion Detection System 4215

cevChassisIDS4235  OBJECT IDENTIFIER
    ::= { cevChassis 497 }

-- Cisco Intrusion Detection System 4235

cevChassisIDS4240  OBJECT IDENTIFIER
    ::= { cevChassis 498 }

-- Cisco Intrusion Prevention System 4240

cevChassisIDS4250  OBJECT IDENTIFIER
    ::= { cevChassis 499 }

-- Cisco Intrusion Detection System 4250

cevChassisIDS4250SX  OBJECT IDENTIFIER
    ::= { cevChassis 500 }

-- Cisco Intrusion Detection System 4250 with fiber interface

cevChassisIDS4250XL  OBJECT IDENTIFIER
    ::= { cevChassis 501 }

-- Cisco Intrusion Detection System 4250 with accelerator card

cevChassisIDS4255  OBJECT IDENTIFIER
    ::= { cevChassis 502 }

-- Cisco Intrusion Prevention System 4255

cevChassisCat375024FS  OBJECT IDENTIFIER
    ::= { cevChassis 503 }

-- Catalyst 3750 24 100BaseFX ports + 2 Ethernet Gigabit SFP ports fixed configuration Layer 2/Layer 3 Ethernet switch.   (SFP:Small Formfactor Pluggable)

cevChassisWSC6504E  OBJECT IDENTIFIER
    ::= { cevChassis 504 }

-- 4 slots chassis in Catalyst 6500 family

cevChassisIGESMSFP  OBJECT IDENTIFIER
    ::= { cevChassis 505 }

-- Cisco Systems Intelligent Gigabit Ethernet Switch Module with SFPs for IBM eServer BladeCenter (OS-CIGESM-18-SFP-E)

cevChasisFe6326K9  OBJECT IDENTIFIER
    ::= { cevChassis 506 }

-- Cisco File Engine Model FE-6326-K9

cevChassisFe7326K9  OBJECT IDENTIFIER
    ::= { cevChassis 508 }

-- Cisco File Engine Model FE-7326-K9

cevChassisFe511K9  OBJECT IDENTIFIER
    ::= { cevChassis 509 }

-- Cisco File Engine Model FE-511-K9

cevChassisSCEDispatcher  OBJECT IDENTIFIER
    ::= { cevChassis 510 }

-- Cisco Service Control Engine Dispatcher

cevChassisSCE2000  OBJECT IDENTIFIER
    ::= { cevChassis 511 }

-- Cisco SCE2000 Service Control Engine

cevChassisSCE1000  OBJECT IDENTIFIER
    ::= { cevChassis 512 }

-- Cisco SCE1000 Service Control Engine

cevChassisAIRAP1240  OBJECT IDENTIFIER
    ::= { cevChassis 513 }

-- Cisco Aironet 1240 series WLAN Access Point with 1 10/100TX port, dual IEEE 802.11a and 802.11g radio ports, external antenna connectors

cevChassisDSC902020K9  OBJECT IDENTIFIER
    ::= { cevChassis 514 }

-- DS-C9020-20K9  - MDS 9020-20K9, 20-Port 4 Gbps Fibre Channel Fabric Switch, Commercial

cevChassisFe611K9  OBJECT IDENTIFIER
    ::= { cevChassis 515 }

-- Cisco File Engine Model FE-611-K9

cevChassisCat3750Ge12SfpDc  OBJECT IDENTIFIER
    ::= { cevChassis 520 }

-- Catalyst 3750 12 Gigabit Ethernet SFP (small Form Factor Plugable) port chassis

cevChassisCat296024  OBJECT IDENTIFIER
    ::= { cevChassis 521 }

-- Catalyst 2960 24 10/100 ports + 2 dual purpose Gigabit Ethernet ports fixed configuration Layer 2 Ethernet switch.

cevChassisCat296048  OBJECT IDENTIFIER
    ::= { cevChassis 522 }

-- Catalyst 2960 48 10/100 ports + 2 dual purpose Gigabit Ethernet ports fixed configuration Layer 2 Ethernet switch.

cevChassisCat2960G24  OBJECT IDENTIFIER
    ::= { cevChassis 523 }

-- Catalyst 2960 20 10/100/1000 ports + 4 dual purpose Gigabit Ethernet ports fixed configuration Layer 2 Ethernet switch.

cevChassisCat2960G48  OBJECT IDENTIFIER
    ::= { cevChassis 524 }

-- Catalyst 2960 44 10/100/1000 ports + 4 dual purpose Gigabit Ethernet ports fixed configuration Layer 2 Ethernet switch.

cevChassisCat6kMsfc2a  OBJECT IDENTIFIER
    ::= { cevChassis 529 }

-- Multilevel Switching Feature Card Version 2a for Catalyst 6000 that is treated as a standalone system by the NMS

cevChassisCe611K9  OBJECT IDENTIFIER
    ::= { cevChassis 530 }

-- Cisco Content Engine Model CE-611-K9

cevChassisME6340ACA  OBJECT IDENTIFIER
    ::= { cevChassis 531 }

-- DSL Switch 48 port ADSL2/2+, Annex A, AC

cevChassisME6340DCA  OBJECT IDENTIFIER
    ::= { cevChassis 532 }

-- DSL Switch 48 port ADSL2/2+, Annex A, DC

cevChassisME6340DCB  OBJECT IDENTIFIER
    ::= { cevChassis 533 }

-- DSL Switch 48 port ADSL2/2+, Annex B, DC

cevChassisCat296024TT  OBJECT IDENTIFIER
    ::= { cevChassis 534 }

-- Catalyst 2960 24 10/100 ports + 2 10/100/1000 ports fixed configuration Layer 2 Ethernet Switch.

cevChassisCat296048TT  OBJECT IDENTIFIER
    ::= { cevChassis 535 }

-- Catalyst 2960 48 10/100 ports + 2 10/100/1000 ports fixed configuration Layer 2 Ethernet Switch.

cevChassisIGESMSFPT  OBJECT IDENTIFIER
    ::= { cevChassis 536 }

-- Cisco Systems Intelligent Gigabit Ethernet Switch Module with SFPs for IBM eServer BladeCenter Telco Chassis (OS-CIGESM-18-SFP-E)

cevChassisMec6524gs8s  OBJECT IDENTIFIER
    ::= { cevChassis 537 }

-- Catalyst 6524 chassis with 24 port SFP and 8 SFP uplinks

cevChassisMec6524gt8s  OBJECT IDENTIFIER
    ::= { cevChassis 538 }

-- Catalyst 6524 chassis with 24 port 10/100/1000BaseT and 8 SFP uplinks

cevChassisPaldron  OBJECT IDENTIFIER
    ::= { cevChassis 541 }

-- ARM Development Platform

cevChassisIGESMT  OBJECT IDENTIFIER
    ::= { cevChassis 542 }

-- Cisco Systems Intelligent Gigabit Ethernet Switch Module for IBM eServer BladeCenter Telco Chassis (OS-CIGESM-18TT-E)

cevChassisCatCE50024TT  OBJECT IDENTIFIER
    ::= { cevChassis 543 }

-- Catalyst Express 500 24 10/100 ports + 2 Gigabit Ethernet ports fixed configuration Layer 2 Ethernet switch

cevChassisCatCE50024LC  OBJECT IDENTIFIER
    ::= { cevChassis 544 }

-- Catalyst Express 500 24 10/100 ports (4 Power Over Ethernet Ports) + 2 dual purpose Gigabit Ethernet ports fixed configuration Layer 2 Ethernet switch

cevChassisCatCE50024PC  OBJECT IDENTIFIER
    ::= { cevChassis 545 }

-- Catalyst Express 500 24 10/100 Power Over Ethernet Ports + 2 dual purpose Gigabit Ethernet ports fixed configuration Layer 2 Ethernet switch

cevChassisCatCE50012TC  OBJECT IDENTIFIER
    ::= { cevChassis 546 }

-- Catalyst Express 500 8 Gigabit Ethernet Ports + 4 dual purpose Gigabit Ethernet ports fixed configuration Layer 2 Ethernet switch

cevChassis5750  OBJECT IDENTIFIER
    ::= { cevChassis 547 }

-- High Assurance Router

cevChassisMWR1941DCA  OBJECT IDENTIFIER
    ::= { cevChassis 548 }

-- The Mobile Wireless Router (MWR-1941-DC-A) is a router with a universal power supply targeted at application in a cell site Base Transceiver Station (BTS) providing backhaul connections to the aggregation node in Radio Access Networks (RAN) and support for AIM module.

cevChassis815  OBJECT IDENTIFIER
    ::= { cevChassis 549 }

-- Cisco 815 platform fixed configuration cable modem router with 4 FastEthernet switch ports, 1 Cable modem port, 1 FastEthernet port

cevChassis240024TSA  OBJECT IDENTIFIER
    ::= { cevChassis 550 }

-- Metro Ethernet 2400, 24 10/100 Fast Ethernet + 2 SFP ports fixed configuration Layer 2 Ethernet switch, AC power.

cevChassis240024TSD  OBJECT IDENTIFIER
    ::= { cevChassis 551 }

-- Metro Ethernet 2400, 24 10/100 Fast Ethernet + 2 SFP ports fixed configuration Layer 2 Ethernet switch, DC power.

cevChassis340024TSA  OBJECT IDENTIFIER
    ::= { cevChassis 552 }

-- Metro Ethernet 3400, 24 10/100 Fast Ethernet + 2 SFP ports fixed configuration Layer 2/3 Ethernet switch, AC power.

cevChassis340024TSD  OBJECT IDENTIFIER
    ::= { cevChassis 553 }

-- Metro Ethernet 3400, 24 10/100 Fast Ethernet + 2 SFP ports fixed configuration Layer 2/3 Ethernet switch, DC power.

cevChassisFe2636  OBJECT IDENTIFIER
    ::= { cevChassis 556 }

-- Cisco File Engine Module  for  26xx and 36xx routers

cevChassisIDS4220  OBJECT IDENTIFIER
    ::= { cevChassis 557 }

-- Cisco Intrusion Detection System 4220

cevChassisIDS4230  OBJECT IDENTIFIER
    ::= { cevChassis 558 }

-- Cisco Intrusion Detection System 4230

cevChassisASA5505  OBJECT IDENTIFIER
    ::= { cevChassis 560 }

-- This is Adaptive Security Appliance (ASA) 5505. This security appliance combines firewall, intrusion prevention, VPN and remote access capabilities.  One expansion slot is provided for additional services

cevChassisWS3020HPQ  OBJECT IDENTIFIER
    ::= { cevChassis 561 }

-- Cisco Catalyst Bladeswitch 3020 for HP

cevChassisWS3030DEL  OBJECT IDENTIFIER
    ::= { cevChassis 562 }

-- Cisco Catalyst Bladeswitch 3030 for Dell

cevChassisWLSE1133  OBJECT IDENTIFIER
    ::= { cevChassis 563 }

-- Chassis for Cisco WLSE 1133

cevChassisASA5550  OBJECT IDENTIFIER
    ::= { cevChassis 564 }

-- This is an Adaptive Security Appliance (ASA) 5550. This security appliance combines firewall, VPN and remote access capabilities.It is a fixed configuration device containing one ASA-SSM-4GE module.

cevChassisWae612K9  OBJECT IDENTIFIER
    ::= { cevChassis 565 }

-- Cisco Wide Area Engine Model WAE-612-K9

cevChassisAirap1250  OBJECT IDENTIFIER
    ::= { cevChassis 567 }

-- Cisco Aironet 1250 series WLAN Access Point with one 10/100/1000TX port and dual IEEE 802.11n radio ports

cevChassisCe512K9  OBJECT IDENTIFIER
    ::= { cevChassis 568 }

-- Cisco Content Engine Model CE-512-K9

cevChassisFe512K9  OBJECT IDENTIFIER
    ::= { cevChassis 569 }

-- Cisco File Engine Model FE-512-K9

cevChassisCe612K9  OBJECT IDENTIFIER
    ::= { cevChassis 570 }

-- Cisco Content Engine Model CE-612-K9

cevChassisFe612K9  OBJECT IDENTIFIER
    ::= { cevChassis 571 }

-- Cisco File Engine Model FE-612-K9

cevChassisOe512K9  OBJECT IDENTIFIER
    ::= { cevChassis 573 }

-- Cisco Optimization Engine Model OE-512-K9

cevChassisOe612K9  OBJECT IDENTIFIER
    ::= { cevChassis 574 }

-- Cisco Optimization Engine Model OE-612-K9

cevChassisCat3750G24WS  OBJECT IDENTIFIER
    ::= { cevChassis 575 }

-- Catalyst 3750 Unified Access Switch with 24 10/100/1000 Power over Ethernet ports + 2 Gigabit Ethernet SFP ports and integrated Wireless Controller

cevChassisCrs14LineCard  OBJECT IDENTIFIER
    ::= { cevChassis 576 }

-- Cisco CRS-1 Series 4 Slots Line Card Chassis

cevChassisMe3400g12CsA  OBJECT IDENTIFIER
    ::= { cevChassis 577 }

-- Metro Ethernet 3400 , 12 GE/SFP ports + 4 SFP ports fixed configuration Layer 2/3 Ethernet switch, AC power

cevChassisMe3400g12CsD  OBJECT IDENTIFIER
    ::= { cevChassis 578 }

-- Metro Ethernet 3400 , 12 GE/SFP ports + 4 SFP ports fixed configuration Layer 2/3 Ethernet switch, DC power

cevChassis877M  OBJECT IDENTIFIER
    ::= { cevChassis 579 }

-- Cisco 877 platform with 1 ADSL Annex M over POTS WAN interface, 4-port 10/100 BASE-T LAN Ethernet switch, hardware encryption and an optional Wireless LAN card

cevChassis1801M  OBJECT IDENTIFIER
    ::= { cevChassis 580 }

-- Cisco 1800 platform with 1 ADSL Annex M over POTS WAN interface, 8-port 10/100 BASE-T LAN Ethernet switch, 1 ISDN BRI S/T interface and an optional Wireless LAN.

cevChassisWsCbs3040Fsc  OBJECT IDENTIFIER
    ::= { cevChassis 581 }

-- Cisco Catalyst Blade Switch 3040 for FSC

cevChassisSpaIPSEC2g2  OBJECT IDENTIFIER
    ::= { cevChassis 582 }

-- IPSec Shared Port Adapter with 2 Gbps DES/3DES/AES (SPA-IPSEC-2G-2)

cevChassisOe511K9  OBJECT IDENTIFIER
    ::= { cevChassis 583 }

-- Cisco Optimization Engine Model OE-511-K9

cevChassisOe611K9  OBJECT IDENTIFIER
    ::= { cevChassis 584 }

-- Cisco Optimization Engine Model OE-611-K9

cevChassisOe7326K9  OBJECT IDENTIFIER
    ::= { cevChassis 585 }

-- Cisco Optimization Engine Model OE-7326-K9

cevChassisMe492410GE  OBJECT IDENTIFIER
    ::= { cevChassis 586 }

-- Metro Ethernet fixed configuration box (ME-4924-10GE) with 2 Ten Gigabit X2 ports and 24+4 One Gigabit SFP ports.

cevChassisDSC9124  OBJECT IDENTIFIER
    ::= { cevChassis 587 }

-- Chassis of 24-port 1/2/4 Gig Supervisor Storage Switch

cevChassisCat3750E48TD  OBJECT IDENTIFIER
    ::= { cevChassis 588 }

-- Catalyst 3750E 48 10/100/1000 ports + 2 TenGigabit Ethernet (X2) ports fixed configuration Layer 2/Layer 3 Ethernet Stackable switch.

cevChassisCat3750E24TD  OBJECT IDENTIFIER
    ::= { cevChassis 589 }

-- Catalyst 3750E 24 10/100/1000 ports + 2 TenGigabit Ethernet (X2) ports fixed configuration Layer 2/Layer 3 Ethernet Stackable switch.

cevChassisCat3750E24PD  OBJECT IDENTIFIER
    ::= { cevChassis 590 }

-- Catalyst 3750E 24 10/100/1000 Power over Ethernet ports + 2 TenGigabit Ethernet (X2) ports fixed configuration Layer 2/Layer 3 Ethernet Stackable switch.

cevChassisCat3750E48PD  OBJECT IDENTIFIER
    ::= { cevChassis 591 }

-- Catalyst 3750E 48 10/100/1000 Power over Ethernet ports + 2 TenGigabit Ethernet (X2) ports fixed configuration Layer 2/Layer 3 Ethernet Stackable switch.

cevChassisCat3560E24TD  OBJECT IDENTIFIER
    ::= { cevChassis 592 }

-- Catalyst 3560E 24 10/100/1000 ports + 2 TenGigabit Ethernet (X2) ports fixed configuration Layer 2/Layer 3 Ethernet Stackable switch.

cevChassisCat3560E48TD  OBJECT IDENTIFIER
    ::= { cevChassis 593 }

-- Catalyst 3560E 48 10/100/1000 ports + 2 TenGigabit Ethernet (X2) ports fixed configuration Layer 2/Layer 3 Ethernet Stackable switch.

cevChassisCat3560E24PD  OBJECT IDENTIFIER
    ::= { cevChassis 594 }

-- Catalyst 3560E 24 10/100/1000 Power over Ethernet ports + 2 TenGigabit Ethernet (X2) ports fixed configuration Layer 2/Layer switch.

cevChassisCat3560E48PD  OBJECT IDENTIFIER
    ::= { cevChassis 595 }

-- Catalyst 3560E 48 10/100/1000 Power over Ethernet ports + 2 TenGigabit Ethernet (X2) ports fixed configuration Layer 2/Layer switch.

cevChassisCat35608PC  OBJECT IDENTIFIER
    ::= { cevChassis 596 }

-- Catalyst 3560 8 10/100 Power over Ethernet ports + 1 dual purpose Gigabit Ethernet Ports fixed configuration Layer 2 /Layer 3 Ethernet Switch.

cevChassisCat29608TC  OBJECT IDENTIFIER
    ::= { cevChassis 597 }

-- Catalyst 2960 8 10/100 Ethernet ports + 1 dual purpose Gigabit Ethernet Port fixed configuration Layer 2 Ethernet Switch.

cevChassisCat2960G8TC  OBJECT IDENTIFIER
    ::= { cevChassis 598 }

-- Catalyst 2960 7 10/100/1000 Ethernet ports + 1 dual purpose Gigabit Ethernet Port fixed configuration Layer 2 Ethernet Switch.

cevChassisCisco7606S  OBJECT IDENTIFIER
    ::= { cevChassis 599 }

-- Cisco Internet Router 7600 S-series Chassis with 6 slots

cevChassisCisco7609S  OBJECT IDENTIFIER
    ::= { cevChassis 600 }

-- Cisco Internet Router 7600 S-series Chassis with 9 slots

cevChassisDSIBMFC  OBJECT IDENTIFIER
    ::= { cevChassis 601 }

-- Chassis of Cisco 4Gb Fibre Channel Switch Module for IBM BladeCenter

cevChassisIPSVirtual  OBJECT IDENTIFIER
    ::= { cevChassis 602 }

-- Cisco Intrusion Prevention System virtual sensor

cevChassis3250  OBJECT IDENTIFIER
    ::= { cevChassis 603 }

-- CISCO 3250 platform Mobile access router chassis.

cevChassis3205WMIC  OBJECT IDENTIFIER
    ::= { cevChassis 604 }

-- Cisco 3205 Wireless MIC (Mobile Interface card) with 802.11a wireless interface in the PC104+ form factor. An interface card for the existing MAR 3200 products(Mobile Access Router)

cevChassisCisco5720  OBJECT IDENTIFIER
    ::= { cevChassis 605 }

-- Integrated Encryption Router

cevChassisMe3400g2csA  OBJECT IDENTIFIER
    ::= { cevChassis 607 }

-- Metro Ethernet 3400, 2 GE/SFP ports + 2 SFP ports fixed configuration Layer 2/3 Ethernet switch, AC power

cevChassis7201  OBJECT IDENTIFIER
    ::= { cevChassis 608 }

-- Cisco 7201 platform, 1 Rack Unit (RU) application specific router with 1 slot

cevChassisNmWae  OBJECT IDENTIFIER
    ::= { cevChassis 609 }

-- Cisco Content Engine Network Module

cevChassisACE4710K9  OBJECT IDENTIFIER
    ::= { cevChassis 610 }

-- ACE 4710 Application Control Engine Appliance

cevChassisN7Kc7010  OBJECT IDENTIFIER
    ::= { cevChassis 612 }

-- Nexus7000 10 slot N7K chassis

cevChassisUbr7225Vxr  OBJECT IDENTIFIER
    ::= { cevChassis 613 }

-- Cisco 7225 Universal Broadband Router, VXR series

cevChassisWSC6509ve  OBJECT IDENTIFIER
    ::= { cevChassis 615 }

-- Catalyst 6500 enhanced 9-slot vertical chassis

cevChassisDSC9134  OBJECT IDENTIFIER
    ::= { cevChassis 616 }

-- Chassis of 32-port 1/2/4 with 10 Gig Supervisor Storage

cevChassisCisco7603S  OBJECT IDENTIFIER
    ::= { cevChassis 617 }

-- Cisco Internet Router 7600 S-series Chassis with 3 slots

cevChassis5740  OBJECT IDENTIFIER
    ::= { cevChassis 620 }

-- Integrated Encryption Router

cevChassis867  OBJECT IDENTIFIER
    ::= { cevChassis 623 }

-- c867 with 1 ADSL2/2+ AnnexA, 4 switch ports, 1 Console/Aux port, and an optional Wireless LAN

cevChassis881  OBJECT IDENTIFIER
    ::= { cevChassis 624 }

-- c881 with 1 FE, 4 switch ports, 1 USB 1.1 port, 1 Console/Aux port, and an optional Wireless LAN

cevChassis881G  OBJECT IDENTIFIER
    ::= { cevChassis 625 }

-- c881G with 1 FE, 4 switch ports, 1 USB 2.0 port, 1 Console/Aux port, 1 3G PCMCIA slot, and an optional Wireless LAN

cevChassisIad881F  OBJECT IDENTIFIER
    ::= { cevChassis 626 }

-- IAD881IF with 1 FE, 4 switch ports, 1 USB 1.1 port, 1 Console/Aux port, 4 FXS ports, and an optional Wireless LAN

cevChassisIad881B  OBJECT IDENTIFIER
    ::= { cevChassis 627 }

-- IAD881B with 1 FE, 4 switch ports, 1 USB 1.1 port, 1 Console/Aux port, 2 PBX BRI ports, and an optional Wireless LAN

cevChassis881Srst  OBJECT IDENTIFIER
    ::= { cevChassis 628 }

-- c881SRST with 1 FE, 4 switch ports, 1 USB 1.1 port, 1 Console/Aux port, 4 FXS ports, 1 PSTN FXO port, and an optional Wireless LAN

cevChassis886  OBJECT IDENTIFIER
    ::= { cevChassis 629 }

-- c886 with 1 ADSL2/2+ AnnexB, 4 switch ports, 1 USB 1.1 port, 1 Console/Aux port, 1 ISDN, and an optional Wireless LAN

cevChassis886G  OBJECT IDENTIFIER
    ::= { cevChassis 630 }

-- c886G with 1 ADSL2/2+ AnnexB, 4 switch ports, 1 USB 2.0 port, 1 Console/Aux port, 1 3G PCMCIA slot, and an optional Wireless LAN

cevChassisIad886F  OBJECT IDENTIFIER
    ::= { cevChassis 631 }

-- IAD886F with 1 ADSL2/2+ AnnexB, 4 switch ports, 1 USB 1.1 port, 1 Console/Aux port, 1 ISDN, 4 FXS ports, and an optional Wireless LAN

cevChassisIad886B  OBJECT IDENTIFIER
    ::= { cevChassis 632 }

-- IAD886B with 1 ADSL2/2+ AnnexB, 4 switch ports, 1 USB 1.1 port, 1 Console/Aux port, 1 ISDN, 2 PBX BRI ports, and an optional LAN

cevChassis886Srst  OBJECT IDENTIFIER
    ::= { cevChassis 633 }

-- c886SRST with 1 ADSL2/2+ AnnexB, 4 switch ports, 1 USB 1.1 port, 1 Console/Aux port, 4 FXS ports, 1 PSTN BRI port,and an optional Wireless LAN

cevChassis887  OBJECT IDENTIFIER
    ::= { cevChassis 634 }

-- c887 with 1 ADSL2/2+ AnnexA, 4 switch ports, 1 USB 1.1 port, 1 Console/Aux port, 1 ISDN, and an optional Wireless LAN

cevChassis887G  OBJECT IDENTIFIER
    ::= { cevChassis 635 }

-- c887G with 1 ADSL2/2+ AnnexA, 4 switch ports, 1 USB 2.0 port, 1 Console/Aux port, 1 3G PCMCIA slot, and an optional Wireless LAN

cevChassisIad887F  OBJECT IDENTIFIER
    ::= { cevChassis 636 }

-- IAD887 with 1 ADSL2/2+ AnnexA, 4 switch ports, 1 USB 1.1 port, 1 Console/Aux port, 1 ISDN, 4 FXS ports, and an optional Wireless LAN

cevChassisIad887B  OBJECT IDENTIFIER
    ::= { cevChassis 637 }

-- IAD887B with 1 ADSL2/2+ AnnexA, 4 switch ports, 1 USB 1.1 port, 1 Console/Aux port, 1 ISDN, 2 PBX BRI ports, and an optional Wireless LAN

cevChassis887Srst  OBJECT IDENTIFIER
    ::= { cevChassis 638 }

-- c887SRST with 1 ADSL2/2+ AnnexA, 4 switch ports, 1 USB 1.1 port, 1 Console/Aux port, 4 FXS ports, 1 PSTN BRI port,and an optional Wireless LAN

cevChassis888G  OBJECT IDENTIFIER
    ::= { cevChassis 640 }

-- c888G with 1 G.SHDSL, 4 switch ports, 1 USB 2.0 port, 1 Console/Aux port, 1 3G PCMCIA slot, and an optional Wireless LAN

cevChassisIad888F  OBJECT IDENTIFIER
    ::= { cevChassis 641 }

-- IAD888F with 1 G.SHDSL, 4 switch ports, 1 USB 1.1 port, 1 Console/Aux port, 1 ISDN, 4 FXS ports, and an optional Wireless LAN

cevChassisIad888B  OBJECT IDENTIFIER
    ::= { cevChassis 642 }

-- IAD888B with 1 G.SHDSL, 4 switch ports, 1 USB 1.1 port, 1 Console/Aux port, 1 ISDN, 2 PBX BRI ports, and an optional Wireless LAN

cevChassis888Srst  OBJECT IDENTIFIER
    ::= { cevChassis 643 }

-- c888SRST with 1 G.SHDSL, 4 switch ports, 1 USB 1.1 port, 1 Console/Aux port, 4 FXS ports, 1 PSTN BRI port, and an optional Wireless LAN

cevChassis891  OBJECT IDENTIFIER
    ::= { cevChassis 644 }

-- c891 with 1 GE, 8 switch ports, 2 USB 2.0 ports, 2 Console/Aux ports, 1 V.92, 1 Backup FE, and an optional Wireless LAN

cevChassis892  OBJECT IDENTIFIER
    ::= { cevChassis 645 }

-- c892 with 1GE, 8 switch ports, 2 USB 2.0 ports, 2 Console/Aux ports, 1 ISDN, 1 Backup FE, and an optional Wireless LAN

cevChassis885D3  OBJECT IDENTIFIER
    ::= { cevChassis 646 }

-- c885-D-3 with 1 US Docsis Cable, 4 switch ports, 1 USB 1.1 port, 1 Console/Aux port, and an optional Wireless LAN

cevChassisIad885FD3  OBJECT IDENTIFIER
    ::= { cevChassis 647 }

-- IAD885F-D-3 with 1 US Docsis Cable, 4 switch ports, 1 USB 1.1 port, 1 Console/Aux port, 4 FXS ports, and an optional Wireless LAN

cevChassis885EJ3  OBJECT IDENTIFIER
    ::= { cevChassis 648 }

-- c885-E/J-3 with 1 Euro-Docsis Cable, 4 switch ports, 1 USB 1.1 port, 1 Console/Aux port, and an optional Wireless LAN

cevChassis7816H  OBJECT IDENTIFIER
    ::= { cevChassis 649 }

-- MCS-7816H class of servers Starting with CCM 6.0 release

cevChassisSce8000  OBJECT IDENTIFIER
    ::= { cevChassis 650 }

-- Cisco SCE8000 Service Control Engine

cevChassisMdsDSC9222i  OBJECT IDENTIFIER
    ::= { cevChassis 651 }

-- MDS 9222i 18-port FC and 4-port GE + 1-slot Modular Switch

cevChassis860Ap  OBJECT IDENTIFIER
    ::= { cevChassis 653 }

-- Cisco 860 AP is the embedded wireless access point module for Cisco 860 router. It has one IEEE 802.11 b/g/n radio port which operates in 2.4 GHz.

cevChassis880Ap  OBJECT IDENTIFIER
    ::= { cevChassis 654 }

-- Cisco 880 AP is the embedded wireless access point module for Cisco 860 router. It has one IEEE 802.11 b/g/n radio port which operates in 2.4 GHz.

cevChassis890Ap  OBJECT IDENTIFIER
    ::= { cevChassis 655 }

-- Cisco 890 AP is the embedded wireless access point module for Cisco 890 router. It has one IEEE 802.11 b/g/n radio port which operates in 2.4 GHz and one IEEE 802.11 a/n radio port which operates in 5 GHz

cevChassis1900Ap  OBJECT IDENTIFIER
    ::= { cevChassis 656 }

-- Cisco 1900 AP is the embedded wireless access point module for Cisco 1900 router. It has one IEEE 802.11 b/g/n radio port which operates in 2.4 GHz and one IEEE 802.11 a/n radio port which operates in 5 GHz

cevChassis340024FSA  OBJECT IDENTIFIER
    ::= { cevChassis 657 }

-- Metro Ethernet 3400, 24 100BaseFX Fast Ethernet + 2 SFP ports fixed configuration Layer 2/3 Ethernet switch, AC power

cevChassisCat4503e  OBJECT IDENTIFIER
    ::= { cevChassis 658 }

-- Catalyst 4500 E-series with 3 slots ( WS-C4503-E )

cevChassisCat4506e  OBJECT IDENTIFIER
    ::= { cevChassis 659 }

-- Catalyst 4500 E-series with 6 slots ( WS-C4506-E )

cevChassisCat4507re  OBJECT IDENTIFIER
    ::= { cevChassis 660 }

-- Catalyst 4500 E-series with 7 slots with redundant supervisors (WS-C4507R-E )

cevChassisCat4510re  OBJECT IDENTIFIER
    ::= { cevChassis 661 }

-- Catalyst 4500 E-series with 10 slots with redundant supervisors (WS-C4510R-E )

cevChassisUc520s8U4FxoK9  OBJECT IDENTIFIER
    ::= { cevChassis 662 }

-- UC500 with support for 8 switch ports and 4 FXO ports

cevChassisUc520s8U4FxoWK9  OBJECT IDENTIFIER
    ::= { cevChassis 663 }

-- UC500 with support for 8 switch ports, 4 FXO ports, and Wi-Fi

cevChassisUc520s8U2BriK9  OBJECT IDENTIFIER
    ::= { cevChassis 664 }

-- UC500 with support for 8 switch ports and 2 BRI

cevChassisUc520s8U2BriWK9  OBJECT IDENTIFIER
    ::= { cevChassis 665 }

-- UC500 with support for 8 switch ports and 2 BRI, and Wi-Fi

cevChassisUc520s16U4FxoK9  OBJECT IDENTIFIER
    ::= { cevChassis 666 }

-- UC500 with support for 16 switch ports and 4 FXO ports

cevChassisUc520s16U4FxoWK9  OBJECT IDENTIFIER
    ::= { cevChassis 667 }

-- UC500 with support for 16 switch ports, 4 FXO ports, and Wi-Fi

cevChassisUc520s16U2BriK9  OBJECT IDENTIFIER
    ::= { cevChassis 668 }

-- UC500 with support for 16 switch ports and 2 BRI

cevChassisUc520s16U2BriWK9  OBJECT IDENTIFIER
    ::= { cevChassis 669 }

-- UC500 with support for 16 switch ports and 2 BRI, and Wi-Fi

cevChassisUc520m32U8FxoK9  OBJECT IDENTIFIER
    ::= { cevChassis 670 }

-- UC500 with support for 32 switch ports and 8 FXO ports

cevChassisUc520m32U8FxoW  OBJECT IDENTIFIER
    ::= { cevChassis 671 }

-- UC500 with support for 32 switch ports and 8 FXO ports, and Wi-Fi

cevChassisUc520m32U4BriK9  OBJECT IDENTIFIER
    ::= { cevChassis 672 }

-- UC500 with support for 32 switch ports and 4 BRI

cevChassisUc520m32U4BriW  OBJECT IDENTIFIER
    ::= { cevChassis 673 }

-- UC500 with support for 32 switch ports and 4 BRI, and Wi-Fi

cevChassisUc520m48U12FxoK9  OBJECT IDENTIFIER
    ::= { cevChassis 674 }

-- UC500 with support for 48 switch ports and 12 FXO ports

cevChassisUc520m48U12FxoW  OBJECT IDENTIFIER
    ::= { cevChassis 675 }

-- UC500 with support for 48 switch ports and 12 FXO ports, and Wi-Fi

cevChassisUc520m48U6BriK9  OBJECT IDENTIFIER
    ::= { cevChassis 676 }

-- UC500 with support for 48 switch ports and 6 BRI

cevChassisUc520m48U6BriW  OBJECT IDENTIFIER
    ::= { cevChassis 677 }

-- UC500 with support for 48 switch ports and 6 BRI, and Wi-Fi

cevChassisUc520m48U1T1E1FK9  OBJECT IDENTIFIER
    ::= { cevChassis 678 }

-- UC500 with support for 48 switch ports, 1 T1E1 and 4 FXO ports

cevChassisUc520m48U1T1E1BK9  OBJECT IDENTIFIER
    ::= { cevChassis 679 }

-- UC500 with support for 48 switch ports , 1 T1E1 and BRI

cevChassisCE5208PC  OBJECT IDENTIFIER
    ::= { cevChassis 680 }

-- Catalyst Express 520 8 10/100 Power over Ethernet ports + 1 dual purpose Gigabit Ethernet Ports fixed configuration Layer 2 Ethernet Switch

cevChassis7828H  OBJECT IDENTIFIER
    ::= { cevChassis 681 }

-- MCS-7828H class of servers Starting with CCM 6.0 release

cevChassis7816I  OBJECT IDENTIFIER
    ::= { cevChassis 682 }

-- MCS-7816I class of servers Starting with CCM 6.0 release

cevChassis7828I  OBJECT IDENTIFIER
    ::= { cevChassis 683 }

-- MCS-7828I class of servers Starting with CCM 6.0 release

cevChassis1861Uc2BK9  OBJECT IDENTIFIER
    ::= { cevChassis 684 }

-- C1861 UC with support for 2 BRI ports and CUE

cevChassis1861Uc4FK9  OBJECT IDENTIFIER
    ::= { cevChassis 685 }

-- C1861 UC with support for 4 FXO ports and CUE

cevChassis1861Srst2BK9  OBJECT IDENTIFIER
    ::= { cevChassis 686 }

-- C1861 SRST with support for 2 BRI ports

cevChassis1861Srst4FK9  OBJECT IDENTIFIER
    ::= { cevChassis 687 }

-- C1861 SRST with support for 4 FXO ports

cevChassisOe7330K9  OBJECT IDENTIFIER
    ::= { cevChassis 688 }

-- Cisco Optimization Engine Model OE-7330-K9

cevChassisOe7350K9  OBJECT IDENTIFIER
    ::= { cevChassis 689 }

-- Cisco Optimization Engine Model OE-7350-K9

cevChassisCat296048TCS  OBJECT IDENTIFIER
    ::= { cevChassis 694 }

-- WS-C2960-48TC-S chassis

cevChassisCat296024TCS  OBJECT IDENTIFIER
    ::= { cevChassis 695 }

-- WS-C2960-24TC-S chassis

cevChassisCat296024S  OBJECT IDENTIFIER
    ::= { cevChassis 696 }

-- WS-C2960-24-S chassis

cevChassisCat296024PC  OBJECT IDENTIFIER
    ::= { cevChassis 697 }

-- WS-C2960-24PC-L chassis

cevChassisCat296024LT  OBJECT IDENTIFIER
    ::= { cevChassis 698 }

-- WS-C2960-24LT-L chassis

cevChassisCat2960PD8TT  OBJECT IDENTIFIER
    ::= { cevChassis 699 }

-- WS-C2960PD-8TT-L chassis

cevChassisASR1002  OBJECT IDENTIFIER
    ::= { cevChassis 700 }

-- Cisco Aggregation Services Router 1000 Series, 2RU Chassis

cevChassisASR1004  OBJECT IDENTIFIER
    ::= { cevChassis 701 }

-- Cisco Aggregation Services Router 1000 Series, 4RU Chassis

cevChassisASR1006  OBJECT IDENTIFIER
    ::= { cevChassis 702 }

-- Cisco Aggregation Services Router 1000 Series, 6RU Chassis

cevChassisWsC4900M  OBJECT IDENTIFIER
    ::= { cevChassis 703 }

-- Catalyst 4900M series chassis with fixed 8 10Gig port base system with 2 additional half height line card slots ( WS-C4900M )

cevChassisASA5580  OBJECT IDENTIFIER
    ::= { cevChassis 704 }

-- This is an Adaptive Security Appliance (ASA) 5580. This security appliance combines firewall, VPN and remote access capabilities. This is a modular chassis with slots for 6 linecards

cevChassisCatRfgw  OBJECT IDENTIFIER
    ::= { cevChassis 705 }

-- RF gateway chassis with 2SUP+10RF+2TCC+12RFSW slots

cevChassisCE52024PC  OBJECT IDENTIFIER
    ::= { cevChassis 706 }

-- Catalyst Express 520 24 10/100 Power over Ethernet ports + 2 dual purpose Gigabit Ethernet Ports fixed configuration Layer 2 Ethernet Switch

cevChassisCE52024LC  OBJECT IDENTIFIER
    ::= { cevChassis 707 }

-- Catalyst Express 520 4 10/100 Power over Ethernet ports + 20 10/100 ports + 2 dual purpose Gigabit Ethernet Ports fixed configuration Layer 2 Ethernet Switch

cevChassisCE52024TT  OBJECT IDENTIFIER
    ::= { cevChassis 708 }

-- Catalyst Express 520 4 10/100 Power over Ethernet ports + 20 10/100 ports + 2 dual purpose Gigabit Ethernet Ports fixed configuration Layer 2 Ethernet Switch.

cevChassisCE520G24TC  OBJECT IDENTIFIER
    ::= { cevChassis 709 }

-- Catalyst Express 520 24 10/100/1000 ports + 2 dual purpose Gigabit Ethernet Ports fixed configuration Layer 2 Ethernet Switch.

cevChassis1861Srst2BCueK9  OBJECT IDENTIFIER
    ::= { cevChassis 710 }

-- C1861 SRST with support for 2 BRI ports and CUE

cevChassis1861Srst4FCueK9  OBJECT IDENTIFIER
    ::= { cevChassis 711 }

-- C1861 SRST with support for 4 FXO ports and CUE

cevChassisVgd1t3  OBJECT IDENTIFIER
    ::= { cevChassis 712 }

-- VGD Voice Gateway with 1xCT3 supporting CCM and MGCP

cevChassisCat3560e12d  OBJECT IDENTIFIER
    ::= { cevChassis 718 }

-- Catalyst 3560E 12 Ten GE (X2) ports

cevChassisN5kC5020pBf  OBJECT IDENTIFIER
    ::= { cevChassis 719 }

-- N5000 2RU Chassis, No Power Supply, 5 Fan Modules, 40 Ports (requires SFP+)

cevChassisN5kC5020pBd  OBJECT IDENTIFIER
    ::= { cevChassis 720 }

-- N5020 Chassis, 1DC PS, 40 SFP+ Ports. Modules Sold Seperate

cevChassisCat3560E12SD  OBJECT IDENTIFIER
    ::= { cevChassis 721 }

-- Catalyst 3560E, 12 SFP Gigabit Ethernet ports + 2 TenGigabit Ethernet (X2) ports

cevChassisOe674  OBJECT IDENTIFIER
    ::= { cevChassis 722 }

-- Cisco Optimization Engine 674

cevChassisIE30004TC  OBJECT IDENTIFIER
    ::= { cevChassis 723 }

-- Cisco Industrial Ethernet 3000 Switch, 4 10/100 + 2 T/SFP

cevChassisIE30008TC  OBJECT IDENTIFIER
    ::= { cevChassis 724 }

-- Cisco Industrial Ethernet 3000 Switch, 4 10/100 + 2 T/SFP

cevChassisRAIE1783MS06  OBJECT IDENTIFIER
    ::= { cevChassis 725 }

-- Rockwell brand Industrial Ethernet  Switch, 4 10/100 + 2 T/SFP

cevChassisRAIE1783MS10T  OBJECT IDENTIFIER
    ::= { cevChassis 726 }

-- Rockwell brand Industrial Ethernet Switch, 8 10/100 + 2 T/SFP

cevChassis2435Iad8Fxs  OBJECT IDENTIFIER
    ::= { cevChassis 727 }

-- IAD2435 with 8FXS, 2FE and 1T1/E1

cevChassisVG204  OBJECT IDENTIFIER
    ::= { cevChassis 728 }

-- Line side Analog Gateway with 4FXS Analog ports

cevChassisVG202  OBJECT IDENTIFIER
    ::= { cevChassis 729 }

-- Line side Analog Gateway with 2FXS Analog ports

cevChassisCat291824TT  OBJECT IDENTIFIER
    ::= { cevChassis 730 }

-- Catalyst 2918 24 10/100 ports + 2 10/100/1000 Ethernet ports fixed configuration Layer 2 Ethernet switch

cevChassisCat291824TC  OBJECT IDENTIFIER
    ::= { cevChassis 731 }

-- Catalyst 2918 24 10/100 ports + 2 dual purpose Gigabit Ethernet ports fixed configuration Layer 2 Ethernet Switch

cevChassisCat291848TT  OBJECT IDENTIFIER
    ::= { cevChassis 732 }

-- Catalyst 2918 48 10/100 ports + 2 10/100/1000 Ethernet ports fixed configuration Layer 2 Ethernet switch

cevChassisCat291848TC  OBJECT IDENTIFIER
    ::= { cevChassis 733 }

-- Catalyst 2918 48 10/100 ports + 2 dual purpose Gigabit Ethernet ports fixed configuration Layer 2 Ethernet switch

cevChassis1805  OBJECT IDENTIFIER
    ::= { cevChassis 734 }

-- Cisco1805 is a repackaging effort for design to address the low end cable access market. C1805 is deployed as cut down and fixed version of Cisco C1841

cevChassisUc52024u4briK9  OBJECT IDENTIFIER
    ::= { cevChassis 735 }

-- UC500 with support for 24U CME Base, CUE and Phone FL w/4BRI, 1VIC

cevChassisUc52024u8fxoK9  OBJECT IDENTIFIER
    ::= { cevChassis 736 }

-- UC 500 with support for 24U CME Base, CUE and Phone FL w/8FXO, 1VIC

cevChassisUc520s8u2briWJK9  OBJECT IDENTIFIER
    ::= { cevChassis 737 }

-- UC500 for Japan with support for 8 switch ports and 2 BRI, and Wi-Fi

cevChassisUc520s16u2briWJK9  OBJECT IDENTIFIER
    ::= { cevChassis 738 }

-- UC500 for Japan with support for 16 switch ports and 2 BRI, and Wi-Fi

cevChassisVSIntSP  OBJECT IDENTIFIER
    ::= { cevChassis 739 }

-- Cisco Video Stream Integrated Services Platform

cevChassisVSSP  OBJECT IDENTIFIER
    ::= { cevChassis 740 }

-- Cisco Video Stream Services Platform

cevChassisVSHydecoder  OBJECT IDENTIFIER
    ::= { cevChassis 741 }

-- Cisco Video Stream Hybrid Decoder

cevChassisVSDecoder  OBJECT IDENTIFIER
    ::= { cevChassis 742 }

-- Cisco Video Stream Decoder

cevChassisVSEncoder1P  OBJECT IDENTIFIER
    ::= { cevChassis 743 }

-- Cisco Video Stream Encoder 1 Port

cevChassisCiscoMwr2941Dc  OBJECT IDENTIFIER
    ::= { cevChassis 745 }

-- The Mobile Wireless Router (MWR-2941-DC) is an environmentally hardened router targeted for application in a cell site Base Transceiver Station (BTS) providing backhaul connections to the aggregation node in Radio Access Networks (RAN).

cevChassisOe574  OBJECT IDENTIFIER
    ::= { cevChassis 746 }

-- Cisco Optimization Engine 574

cevChassisOe474  OBJECT IDENTIFIER
    ::= { cevChassis 747 }

-- Cisco Optimization Engine 474

cevChassisOe274  OBJECT IDENTIFIER
    ::= { cevChassis 748 }

-- Cisco Optimization Engine 274

cevChassis7816c  OBJECT IDENTIFIER
    ::= { cevChassis 749 }

-- MCS-7816C class of servers Base model CAM-16

cevChassisAp801agn  OBJECT IDENTIFIER
    ::= { cevChassis 750 }

-- Cisco AP801 Access Point with dual IEEE 802.11a/g/n radio ports

cevChassisAp801gn  OBJECT IDENTIFIER
    ::= { cevChassis 751 }

-- Cisco AP801 Access Point with single IEEE 802.11g/n radio port

cevChassisC1861WSrst4FCueK9  OBJECT IDENTIFIER
    ::= { cevChassis 752 }

-- C1861 SRST with support for 4 FXO ports, Wireless and CUE

cevChassisC1861WSrst2BCueK9  OBJECT IDENTIFIER
    ::= { cevChassis 753 }

-- C1861 SRST with support for 2 BRI ports, Wireless and CUE

cevChassisC1861WSrst4FK9  OBJECT IDENTIFIER
    ::= { cevChassis 754 }

-- C1861 SRST with support for 4 FXO ports and Wireless

cevChassisC1861WSrst2BK9  OBJECT IDENTIFIER
    ::= { cevChassis 755 }

-- C1861 SRST with support for 2 BRI ports and Wireless

cevChassisC1861WUc4FK9  OBJECT IDENTIFIER
    ::= { cevChassis 756 }

-- C1861 UC with support for 4 FXO ports, Wireless and CUE

cevChassisC1861WUc2BK9  OBJECT IDENTIFIER
    ::= { cevChassis 757 }

-- support for 2 BRI ports, Wireless and CUE

cevChassisMe3400e24tsM  OBJECT IDENTIFIER
    ::= { cevChassis 758 }

-- Metro Ethernet 3400E, 24 10/100 Fast Ethernet + 2 SFP ports fixed configuration Layer 2/3 Ethernet switch, modular power

cevChassisMe3400eg12csM  OBJECT IDENTIFIER
    ::= { cevChassis 759 }

-- Metro Ethernet 3400 , 12 GE/SFP ports + 4 SFP ports fixed configuration Layer 2/3 Ethernet switch, modular power

cevChassisMe3400eg2csA  OBJECT IDENTIFIER
    ::= { cevChassis 760 }

-- Metro Ethernet 3400E, 2 GE/SFP ports + 2 SFP ports fixed configuration Layer 2/3 Ethernet switch, AC power

cevChassisCe674  OBJECT IDENTIFIER
    ::= { cevChassis 761 }

-- Cisco Content Engine 674

cevChassisCAM35  OBJECT IDENTIFIER
    ::= { cevChassis 762 }

-- Four port GigE Common Appliance Model 35 for Service Control Operating System

cevChassisCe7341  OBJECT IDENTIFIER
    ::= { cevChassis 763 }

-- Cisco Content Engine  7341

cevChassisCe7371  OBJECT IDENTIFIER
    ::= { cevChassis 764 }

-- Cisco Content Engine  7371

cevChassisWsCbs3125gS  OBJECT IDENTIFIER
    ::= { cevChassis 768 }

-- Cisco Catalyst Blade Switch 3125G for HP

cevChassisWsC492810GE  OBJECT IDENTIFIER
    ::= { cevChassis 770 }

-- Catalyst 4000 series fixed configuration switch with  28 One Gigabit SFP ports and 2 Ten Gigabit X2 ports

cevChassisCat296048TTS  OBJECT IDENTIFIER
    ::= { cevChassis 771 }

-- Catalyst 2960 48 10/100 ports + 2 10/100/1000 Ethernet ports fixed configuration Layer 2 Ethernet switch

cevChassisCat29608TCS  OBJECT IDENTIFIER
    ::= { cevChassis 772 }

-- Catalyst 2960 8 10/100 ports + 1 dual purpose Gigabit Ethernet port fixed configuration Layer 2 Ethernet switch

cevChassisSr520FE  OBJECT IDENTIFIER
    ::= { cevChassis 774 }

-- SR520 with 1 10/100T ethernet WAN interface, 4-port 10/100 Base-T LAN Ethernet switch, hardware encryption and an optional Wireless LAN card

cevChassisSr520ADSL  OBJECT IDENTIFIER
    ::= { cevChassis 775 }

-- SR520 with 1 ADSL over POTS WAN interface, 4-port 10/100 BASE-T LAN Ethernet switch, hardware encryption and an optional Wireless LAN card

cevChassisSr520ADSLi  OBJECT IDENTIFIER
    ::= { cevChassis 776 }

-- SR520 with 1 ADSL over ISDN WAN interface, 4-port 10/100 Base-T LAN Ethernet switch, hardware encryption and an optional Wireless LAN card

cevChassisN7Kc7018  OBJECT IDENTIFIER
    ::= { cevChassis 777 }

-- Nexus7000 18 slot N7K chassis

cevChassisCat356012PCS  OBJECT IDENTIFIER
    ::= { cevChassis 778 }

-- Catalyst 3560 12 10/100 Power over Ethernet ports + 1 dual purpose Gigabit Ethernet port fixed configuration Layer 2 Ethernet switch

cevChassisCat296048PSTL  OBJECT IDENTIFIER
    ::= { cevChassis 779 }

-- Catalyst 2960 48 10/100 Power over Ethernet ports + 2 10/100/1000 Ethernet Ports + 2 SFP fixed configuration Layer 2 Ethernet switch

cevChassisASR9010  OBJECT IDENTIFIER
    ::= { cevChassis 780 }

-- Cisco Aggregation Services Router (ASR) 9010 Chassis

cevChassisASR9006  OBJECT IDENTIFIER
    ::= { cevChassis 781 }

-- Cisco Aggregation Services Router (ASR) 9006 Chassis

cevChassisASR14K4  OBJECT IDENTIFIER
    ::= { cevChassis 782 }

-- Cisco ASR14000 Series 4-Slot Chassis

cevChassisASR14K8  OBJECT IDENTIFIER
    ::= { cevChassis 783 }

-- Cisco ASR14000 Series 8-Slot Chassis

cevChassisCat3560v224tsD  OBJECT IDENTIFIER
    ::= { cevChassis 784 }

-- 24 10/100 ports + 2 Ethernet Gigabit SFP ports fixed configuration Layer 2/Layer 3 Ethernet Non-stackable switch, DC power

cevChassisCat3560v224ts  OBJECT IDENTIFIER
    ::= { cevChassis 785 }

-- 24 10/100 ports + 2 Ethernet Gigabit SFP ports fixed configuration Layer 2/Layer 3 Ethernet Non-stackable switch

cevChassisCat3560v224ps  OBJECT IDENTIFIER
    ::= { cevChassis 786 }

-- 24 10/100 ports + 2 Ethernet Gigabit SFP ports fixed configuration Layer 2/Layer 3 Ethernet Non-stackable PoE switch

cevChassisCat3750v224ts  OBJECT IDENTIFIER
    ::= { cevChassis 787 }

-- 24 10/100 ports + 2 Ethernet Gigabit SFP ports fixed configuration Layer 2/Layer 3 Ethernet Stackable switch

cevChassisCat3750v224ps  OBJECT IDENTIFIER
    ::= { cevChassis 788 }

-- 24 10/100 ports + 2 Ethernet Gigabit SFP ports fixed configuration Layer 2/Layer 3 Ethernet Stackable PoE switch

cevChassisCat3560v248ts  OBJECT IDENTIFIER
    ::= { cevChassis 789 }

-- 48 10/100 ports + 4 Ethernet Gigabit SFP ports fixed configuration Layer 2/Layer 3 Ethernet Non-stackable switch

cevChassisCat3560v248ps  OBJECT IDENTIFIER
    ::= { cevChassis 790 }

-- 48 10/100 ports + 4 Ethernet Gigabit SFP ports fixed configuration Layer 2/Layer 3 Ethernet Non-stackable PoE switch

cevChassisCat3750v248ts  OBJECT IDENTIFIER
    ::= { cevChassis 791 }

-- 48 10/100 ports + 4 Ethernet Gigabit SFP ports fixed configuration Layer 2/Layer 3 Ethernet Stackable switch

cevChassisCat3750v248ps  OBJECT IDENTIFIER
    ::= { cevChassis 792 }

-- 48 10/100 ports + 4 Ethernet Gigabit SFP ports fixed configuration Layer 2/Layer 3 Ethernet Stackable PoE switch

cevChassisAirbr1430  OBJECT IDENTIFIER
    ::= { cevChassis 793 }

-- Cisco 1400 series wireless LAN bridge with three Gigabit Ethernet ports and one 802.11A radio

cevChassisNamApp2204rj45  OBJECT IDENTIFIER
    ::= { cevChassis 794 }

-- Cisco NAM Appliance 2204 with RJ45 connector

cevChassisNamApp2220  OBJECT IDENTIFIER
    ::= { cevChassis 795 }

-- Cisco NAM Appliance 2220

cevChassisAIRAP1141  OBJECT IDENTIFIER
    ::= { cevChassis 796 }

-- Cisco Aironet 1140 series WLAN Access Point with one 10/100/1000TX port and single IEEE 802.11n radio port

cevChassisAIRAP1142  OBJECT IDENTIFIER
    ::= { cevChassis 797 }

-- Cisco Aironet 1140 series WLAN Access Point with one 10/100/1000TX port and dual IEEE 802.11n radio ports

cevChassisN5kC5010pBf  OBJECT IDENTIFIER
    ::= { cevChassis 798 }

-- N5000 1RU Chassis no Power Supply 2 Fan Modules 20 ports (req SFP+)

cevChassisASR9010DC  OBJECT IDENTIFIER
    ::= { cevChassis 799 }

-- ASR-9010 DC Chassis

cevChassisASR9006DC  OBJECT IDENTIFIER
    ::= { cevChassis 800 }

-- ASR-9006 DC Chassis

cevChassis18xxx  OBJECT IDENTIFIER
    ::= { cevChassis 801 }

-- BETA of 18000 family router

cevChassisc887Vdsl2  OBJECT IDENTIFIER
    ::= { cevChassis 802 }

-- c887Vdsl2 with 1 VDSL2 only over POTS, 4 switch ports, 1 USB 1.1 port, 1 Console/Aux port and 1 ISDN

cevChassisC1941  OBJECT IDENTIFIER
    ::= { cevChassis 803 }

-- Cisco 1941 Chassis(2 GE, 2 EHWIC)

cevChassisC2901  OBJECT IDENTIFIER
    ::= { cevChassis 804 }

-- Cisco 2901 Chassis(2 GE, 4 EHWIC, 2 DSP)

cevChassisC2911  OBJECT IDENTIFIER
    ::= { cevChassis 805 }

-- Cisco 2911 Chassis(3 GE, 4 EHWIC, 1 SM, 2 DSP)

cevChassisC2921  OBJECT IDENTIFIER
    ::= { cevChassis 806 }

-- Cisco 2921 Chassis(3 GE, 4 EHWIC,  1 SM, 3 DSP)

cevChassisC2951  OBJECT IDENTIFIER
    ::= { cevChassis 807 }

-- Cisco 2951 Chassis(3 GE, 4 EHWIC, 2 SM, 3 DSP)

cevChassisC3925  OBJECT IDENTIFIER
    ::= { cevChassis 808 }

-- Cisco 3925 Chassis(slot for SPE, 2 SM slots, dual PS slots)

cevChassisC3945  OBJECT IDENTIFIER
    ::= { cevChassis 809 }

-- Cisco 3945 Chassis(slot for SPE, 4 SM slots, dual PS slots)

cevChassisEsw52024pK9  OBJECT IDENTIFIER
    ::= { cevChassis 810 }

-- 24-port 10/100 Ethernet Switch with PoE

cevChassisEsw54024pK9  OBJECT IDENTIFIER
    ::= { cevChassis 811 }

-- 24-port 10/100/1000 Ethernet Switch with PoE

cevChassisEsw52048pK9  OBJECT IDENTIFIER
    ::= { cevChassis 812 }

-- 48-port 10/100 Ethernet Switch with PoE

cevChassisEsw52024K9  OBJECT IDENTIFIER
    ::= { cevChassis 813 }

-- 24-port 10/100 Ethernet Switch

cevChassisEsw54024K9  OBJECT IDENTIFIER
    ::= { cevChassis 814 }

-- 24-port 10/100/1000 Ethernet Switch

cevChassisEsw52048K9  OBJECT IDENTIFIER
    ::= { cevChassis 815 }

-- 48-port 10/100 Ethernet Switch

cevChassisEsw54048K9  OBJECT IDENTIFIER
    ::= { cevChassis 816 }

-- 48-port 10/100/1000 Ethernet Switch

cevChassisNamApp2204sfp  OBJECT IDENTIFIER
    ::= { cevChassis 817 }

-- Cisco NAM Appliance 2204 with SFP connector

cevChassisSR520T1  OBJECT IDENTIFIER
    ::= { cevChassis 818 }

-- This is a voice and data platform with 2 FE and 1 T1 port. This is done by Small Business Technology Group

cevChassisN2kC2148T1GE  OBJECT IDENTIFIER
    ::= { cevChassis 820 }

-- Nexus 2000 Series 1GE Fabric Extender, 1PS, 1 Fan Module, 48x1G-BaseT + 4x10GE (req SFP+)

cevChassisC1941W  OBJECT IDENTIFIER
    ::= { cevChassis 827 }

-- Cisco 1941 Chassis (2 GE, 2 EHWIC, 802.11n WLAN)

cevChassisC888E  OBJECT IDENTIFIER
    ::= { cevChassis 828 }

-- c888E with 1 EFM based 4 port G.SHDSL , 4 switch ports, 1 USB 1.1 port, 1 Console/Aux port, 1 ISDN, and an optional Wireless LAN

cevChassisC888EG  OBJECT IDENTIFIER
    ::= { cevChassis 829 }

-- c888EG with 1 EFM based 4 pair G.SHDSL, 4 switch ports, 1 USB 2.0 port, 1 Console/Aux port, 1 3G PCMCIA slot, and an optional Wireless LAN

cevChassisIad888EF  OBJECT IDENTIFIER
    ::= { cevChassis 830 }

-- IAD888EF with 1 EFM based 4 pair G.SHDSL, 4 switch ports, 1 USB 1.1 port, 1 Console/Aux port, 1 ISDN, 4 FXS ports, and an optional Wireless LAN

cevChassisIad888EB  OBJECT IDENTIFIER
    ::= { cevChassis 831 }

-- IAD888EB with 1 EFM based 4 pair G.SHDSL, 4 switch ports, 1 USB 1.1 port, 1 Console/Aux port, 1 ISDN, 2 PBX BRI ports, and an optional Wireless LAN

cevChassisC888ESRST  OBJECT IDENTIFIER
    ::= { cevChassis 832 }

-- c888ESRST with 1 EFM based 4 pair G.SHDSL, 4 switch ports, 1 USB 1.1 port, 1 Console/Aux port, 4 FXS ports, 1 PSTN BRI port, and an optional Wireless LAN

cevChassis3845nv  OBJECT IDENTIFIER
    ::= { cevChassis 833 }

-- Four Network Module Slots, Four WIC slots, Two Gigabit Ethernet ports 3800nv family router

cevChassis3825nv  OBJECT IDENTIFIER
    ::= { cevChassis 834 }

-- Two Network Module Slots, Four WIC slots, Two Gigabit Ethernet ports 3800nv family router

cevChassisWSC235048TD  OBJECT IDENTIFIER
    ::= { cevChassis 836 }

-- Catalyst 2350 48 10/100/1000 ports + 2 TenGigabit Ethernet (X2) ports fixed configuration Layer 2 Ethernet Switch

cevChassis887M  OBJECT IDENTIFIER
    ::= { cevChassis 837 }

-- c887 with 1 ADSL2/2+ AnnexM, 4 switch ports, 1 USB 1.1 port, 1 Console/Aux port,1 ISDN, and an optional Wireless LAN

cevChassisASR9010AC  OBJECT IDENTIFIER
    ::= { cevChassis 838 }

-- ASR-9010 AC Chassis

cevChassisASR9006AC  OBJECT IDENTIFIER
    ::= { cevChassis 839 }

-- ASR-9006 AC Chassis

cevChassisN1KV  OBJECT IDENTIFIER
    ::= { cevChassis 840 }

-- Nexus1000V chassis

cevChassisUCSN10S6100  OBJECT IDENTIFIER
    ::= { cevChassis 847 }

-- Cisco UCS Unified Computing System 6120XP 20 Port Fabric Interconnect

cevChassisCDScde420  OBJECT IDENTIFIER
    ::= { cevChassis 848 }

-- Cisco Content Delivery System Model CDE-420

cevChassisCDScde220  OBJECT IDENTIFIER
    ::= { cevChassis 849 }

-- Cisco Content Delivery System Model CDE-220

cevChassisCDScde110  OBJECT IDENTIFIER
    ::= { cevChassis 850 }

-- Cisco Content Delivery System Model CDE-110

cevChassisCiscoCeVirtualBlade  OBJECT IDENTIFIER
    ::= { cevChassis 851 }

-- Cisco Content Engine Virtual Blade

cevChassisASR1002F  OBJECT IDENTIFIER
    ::= { cevChassis 852 }

-- Cisco Aggregation Services Router 1000 Series, 2RU Fixed Chassis

cevChassisADE2120  OBJECT IDENTIFIER
    ::= { cevChassis 853 }

-- Application Deployment Engine - Intel Conroe processor HDD 2x250GB Memory 4x1GB NIC 2x1GE

cevChassisAIRAP3501  OBJECT IDENTIFIER
    ::= { cevChassis 860 }

-- Cisco Aironet 3500 Series WLAN Access Point with one 10/100/1000TX port and single IEEE 802.11n radio port

cevChassisAIRAP3502  OBJECT IDENTIFIER
    ::= { cevChassis 861 }

-- Cisco Aironet 3500 Series WLAN Access Point with one 10/100/1000TX port and dual IEEE 802.11n radio ports

cevChassisCDScde200  OBJECT IDENTIFIER
    ::= { cevChassis 862 }

-- Cisco Content Delivery System Model CDE-200

cevChassisCDScde100  OBJECT IDENTIFIER
    ::= { cevChassis 863 }

-- Cisco Content Delivery System Model CDE-100

cevChassisCDScde300  OBJECT IDENTIFIER
    ::= { cevChassis 864 }

-- Cisco Content Delivery System Model CDE-300

cevChassisCDScde400  OBJECT IDENTIFIER
    ::= { cevChassis 865 }

-- Cisco Content Delivery System Model CDE-400

cevChassisSps2004B  OBJECT IDENTIFIER
    ::= { cevChassis 869 }

-- Metro Ethernet Switch with 1 1000Base-BX-U WAN port and 5 10/100/1000M LAN ports

cevChassisSps204B  OBJECT IDENTIFIER
    ::= { cevChassis 870 }

-- Metro Ethernet Switch with 1 100Base-BX-U WAN and 5 10/100/1000M LAN ports

cevChassisAp541nAK9  OBJECT IDENTIFIER
    ::= { cevChassis 874 }

-- 802.11a/b/g/n Wireless LAN Access Point for North America, FCC band plan

cevChassisAp541nEK9  OBJECT IDENTIFIER
    ::= { cevChassis 875 }

-- 802.11a/b/g/n Wireless LAN Access Point for Europe, ETSI band plan

cevChassisAp541nNK9  OBJECT IDENTIFIER
    ::= { cevChassis 876 }

-- 802.11a/b/g/n Wireless LAN Access Point for ANZ band plan

cevChassisSRP521  OBJECT IDENTIFIER
    ::= { cevChassis 877 }

-- Service Ready Platform router with Fast Ethernet WAN port

cevChassisSRP526  OBJECT IDENTIFIER
    ::= { cevChassis 878 }

-- Service Ready Platform router with ADSL2+ over ISDN WAN port

cevChassisSRP527  OBJECT IDENTIFIER
    ::= { cevChassis 879 }

-- Service Ready Platform router with ADSL2+ over POTS WAN port

cevChassisSRP541  OBJECT IDENTIFIER
    ::= { cevChassis 880 }

-- Service Ready Platform router with GE WAN port

cevChassisSRP546  OBJECT IDENTIFIER
    ::= { cevChassis 881 }

-- Service Ready Platform router with ADSL2+ over ISDN WAN port as well as GE WAN port

cevChassisSRP547  OBJECT IDENTIFIER
    ::= { cevChassis 882 }

-- Service Ready Platform router with ADSL2+ over POTS WAN port as well as GE WAN port

cevChassisVS510FXO  OBJECT IDENTIFIER
    ::= { cevChassis 883 }

-- Call control solution for 4-24 phone

cevChassis887GVdsl2  OBJECT IDENTIFIER
    ::= { cevChassis 884 }

-- c887G with 1 VDSL2 only over POTS, 4 switch ports, 1 USB 2.0 port, 1 Console/Aux port, 1 3G PCMCIA slot, and an optional Wireless LAN

cevChassis887SrstVdsl2  OBJECT IDENTIFIER
    ::= { cevChassis 885 }

-- c887SRSTVdsl2 with 1 VDSL2 over POTS, 4 switch ports, 1 USB 1.1 port, 1 Console/Aux port, 4 FXS ports, 1 PSTN BRI port,and an optional Wireless LAN

cevChassis59xx  OBJECT IDENTIFIER
    ::= { cevChassis 895 }

-- Chassis Type for 59xx embedded services family of routers

cevChassisCat296024LCS  OBJECT IDENTIFIER
    ::= { cevChassis 896 }

-- Catalyst 2960 8 10/100 Power over Ethernet ports + 16 10/100 Ethernet ports + 2 dual purpose Gigabit Ethernet ports fixed configuration Layer 2 Ethernet switch

cevChassisCat296024PCS  OBJECT IDENTIFIER
    ::= { cevChassis 897 }

-- Catalyst 2960 24 10/100 Power over Ethernet ports + 2 dual purpose Gigabit Ethernet ports fixed configuration Layer 2 Ethernet switch

cevChassisCat296048PSTS  OBJECT IDENTIFIER
    ::= { cevChassis 898 }

-- Catalyst 2960 48 10/100 Power over Ethernet ports + 2 10/100/1000 Ethernet ports + 2 SFP ports fixed configuration Layer 2 Ethernet switch

cevChassisCiscoNMWAE900  OBJECT IDENTIFIER
    ::= { cevChassis 900 }

-- Cisco Network Module Intergrated Service Engine 900

cevChassisCiscoNMWAE700  OBJECT IDENTIFIER
    ::= { cevChassis 901 }

-- Cisco Network Module Intergrated Service Engine 700

cevChassis5940  OBJECT IDENTIFIER
    ::= { cevChassis 902 }

-- Chassis Type for 5940 embedded services family of routers

cevChassisN4KIBMEth  OBJECT IDENTIFIER
    ::= { cevChassis 903 }

-- Chassis of Cisco 10Gb Ethernet Switch Module for IBM BladeCenter

cevChassisASR1001  OBJECT IDENTIFIER
    ::= { cevChassis 904 }

-- Cisco Aggregation Services Router 1000 Series, 1RU Chassis

cevChassisASR1013  OBJECT IDENTIFIER
    ::= { cevChassis 905 }

-- Cisco Aggregation Services Router 1000 Series, 13RU Chassis

cevChassisCDScde205  OBJECT IDENTIFIER
    ::= { cevChassis 906 }

-- Cisco Content Delivery System Model CDE-205

cevChassisNexus1010  OBJECT IDENTIFIER
    ::= { cevChassis 907 }

-- Nexus1010 Chassis

cevChassisRaie1783Rms06t  OBJECT IDENTIFIER
    ::= { cevChassis 908 }

-- Cisco Rockwell brand Layer 3 Industrial Ethernet Switch, 4 10/100 + 2 T/SFP

cevChassisRaie1783Rms10t  OBJECT IDENTIFIER
    ::= { cevChassis 909 }

-- Rockwell brand Industrial Ethernet Switch, 8 10/100 + 2 T/SFP

cevChassisMXE5600  OBJECT IDENTIFIER
    ::= { cevChassis 910 }

-- Cisco MXE 5600 platform,  1 Rack Unit (RU) application specific device with 8 slots

cevChassisEsw5408pK9  OBJECT IDENTIFIER
    ::= { cevChassis 911 }

-- Cisco ESW 540 8-port 10/100/1000 PoE switch

cevChassisEsw5208pK9  OBJECT IDENTIFIER
    ::= { cevChassis 912 }

-- Cisco ESW 520 8-port 10/100 PoE switch

cevChassisN2kC2232PP10GE  OBJECT IDENTIFIER
    ::= { cevChassis 913 }

-- N2K 10GE FEX, 1PS

cevChassisN2kC2248TP1GE  OBJECT IDENTIFIER
    ::= { cevChassis 914 }

-- N2K 1GE FEX, 1PS, 1 Fan Module, 48x1G-BaseT+4x10GE SFP+ (req SFP+ optics)

cevChassisWsC4948e10GE  OBJECT IDENTIFIER
    ::= { cevChassis 915 }

-- Catalyst 4000 series fixed configuration switch with 48 10/100/1000BaseT ports and four 10Gbps/1Gbps SFP+/SF ports(WS-C4948E)

cevChassis1921k9  OBJECT IDENTIFIER
    ::= { cevChassis 928 }

-- Cisco 1921/K9 Chassis(2 GE, 2 EHWIC)

cevChassis1905k9  OBJECT IDENTIFIER
    ::= { cevChassis 929 }

-- Cisco 1905/K9 Chassis(2 GE, Serial 1T, 1 EHWIC)

cevChassisN4KIBMCiscoEth  OBJECT IDENTIFIER
    ::= { cevChassis 930 }

-- Chassis of Cisco 10Gb Ethernet Switch Module for IBM BladeCenter Cisco sold version

cevChassisASA5585  OBJECT IDENTIFIER
    ::= { cevChassis 931 }

-- Chassis type for Adaptive Security Appliance 5585 that features multiple expansion module slots, and multi-gigabit performance

cevChassisN7Kc7009  OBJECT IDENTIFIER
    ::= { cevChassis 932 }

-- N7K-C7009 nexus-9-slot chassis

cevChassisMwr2941DcA  OBJECT IDENTIFIER
    ::= { cevChassis 933 }

-- Wireless Router (MWR-2941-DC) is an environmentally hardened router

cevChassisOeNm302  OBJECT IDENTIFIER
    ::= { cevChassis 937 }

-- Cisco Optimization Engine Network Module 302

cevChassisOeNm502  OBJECT IDENTIFIER
    ::= { cevChassis 938 }

-- Cisco Optimization Engine Network Module 502

cevChassisOeNm522  OBJECT IDENTIFIER
    ::= { cevChassis 939 }

-- Cisco Optimization Engine Network Module 522

cevChassisOeSmSre700  OBJECT IDENTIFIER
    ::= { cevChassis 940 }

-- Cisco Optimization Engine Service Module Service Ready Engine 700

cevChassisOeSmSre900  OBJECT IDENTIFIER
    ::= { cevChassis 941 }

-- Cisco Optimization Engine Service Module Service Ready Engine 900

cevChassisCDScde2202s3  OBJECT IDENTIFIER
    ::= { cevChassis 944 }

-- Cisco Content Delivery System Model CDE-220-2S3

cevChassisWsC3750x24  OBJECT IDENTIFIER
    ::= { cevChassis 945 }

-- Catalyst 3750X 24 10/100/1000 Ports + 4 SFP Ports + 2 SFP+ Ports Layer 2/Layer 3 Ethernet Stackable Switch

cevChassisWsC3750x48  OBJECT IDENTIFIER
    ::= { cevChassis 946 }

-- Catalyst 3750X 48 10/100/1000 Ports + 4 SFP Ports + 2 SFP+ Ports Layer 2/Layer 3 Ethernet Stackable Switch

cevChassisWsC3750x24P  OBJECT IDENTIFIER
    ::= { cevChassis 947 }

-- Catalyst 3750X 24 10/100/1000 PoE Ports + 4 SFP Ports + 2 SFP+ Ports Layer 2/Layer 3 Ethernet Stackable Switch

cevChassisWsC3750x48P  OBJECT IDENTIFIER
    ::= { cevChassis 948 }

-- Catalyst 3750X 48 10/100/1000 PoE Ports + 4 SFP Ports + 2 SFP+ Ports Layer 2/Layer 3 Ethernet Stackable Switch

cevChassisWsC3560x24  OBJECT IDENTIFIER
    ::= { cevChassis 949 }

-- Catalyst 3560X 24 10/100/1000 Ports + 4 SFP Ports + 2 SFP+ Ports Layer 2/Layer 3 Ethernet Switch

cevChassisWsC3560x48  OBJECT IDENTIFIER
    ::= { cevChassis 950 }

-- Catalyst 3560X 48 10/100/1000 Ports + 4 SFP Ports + 2 SFP+ Ports Layer 2/Layer 3 Ethernet Switch

cevChassis1841Ck9  OBJECT IDENTIFIER
    ::= { cevChassis 957 }

-- 1841C/K9 data only router with 2 HWIC slots

cevChassis2801Ck9  OBJECT IDENTIFIER
    ::= { cevChassis 958 }

-- 2801C/K9 router with 4 HWIC slots

cevChassis2811Ck9  OBJECT IDENTIFIER
    ::= { cevChassis 959 }

-- 2811C/K9 router with two integrated fast ethernets and integrated VPN

cevChassis2821Ck9  OBJECT IDENTIFIER
    ::= { cevChassis 960 }

-- 2821C/K9 router with two integrated gigabit ethernets and integrated VPN

cevChassis3825Ck9  OBJECT IDENTIFIER
    ::= { cevChassis 962 }

-- 3825C/K9 router with Two Network Module Slots, Four WIC slots, Two Gigabit Ethernet ports

cevChassis3845Ck9  OBJECT IDENTIFIER
    ::= { cevChassis 963 }

-- 3845C/K9 router with Four Network Module Slots, Four WIC slots, Two Gigabit Ethernet ports

cevChassisAIRAP1262  OBJECT IDENTIFIER
    ::= { cevChassis 966 }

-- Cisco Aironet 1260 Series WLAN Access Point with one 10/100/1000TX port and dual IEEE 802.11n radio ports

cevChassisAIRAP1261  OBJECT IDENTIFIER
    ::= { cevChassis 967 }

-- Cisco Aironet 1260 Series WLAN Access Point with one 10/100/1000TX port and single IEEE 802.11n radio port

cevChassis892F  OBJECT IDENTIFIER
    ::= { cevChassis 968 }

-- c892F with 1 GE/SFP port, 8 switch ports, 2 USB 2.0 ports, 2 Console/Aux ports, 1 ISDN, 1 Backup FE, and an optional Wireless LAN

cevChassisMe3600x24fsM  OBJECT IDENTIFIER
    ::= { cevChassis 969 }

-- Cisco ME 3600X Ethernet Access Switch, 24 GE SFP ports + 2 10Gbps/1Gbps SFP+/SFP ports fixed configuration Layer 2/3 Ethernet switch, modular power

cevChassisMe3600x24tsM  OBJECT IDENTIFIER
    ::= { cevChassis 970 }

-- Cisco ME 3600X Ethernet Access Switch, 24 10/100/1000 ports + 2 10Gbps/1Gbps SFP+/SFP ports fixed configuration Layer 2/3 Ethernet switch, modular power

cevChassisMe3800x24fsM  OBJECT IDENTIFIER
    ::= { cevChassis 971 }

-- Cisco ME 3800X Carrier Ethernet Switch Router, 24 GE SFP ports + 2 10Gbps/1Gbps SFP+/SFP ports fixed configuration Layer 2/3 Carrier Ethernet Switch Router, modular power

cevChassisCGR2010  OBJECT IDENTIFIER
    ::= { cevChassis 972 }

-- Cisco Connected Grid Router 2010 Chassis(2 GE, 4 GRWIC)

cevChassisWsC2960s48tsS  OBJECT IDENTIFIER
    ::= { cevChassis 973 }

-- Catalyst 2960S 48 Gig Downlinks and 2 SFP uplink, Nonstackable module

cevChassisWsC2960s24tsS  OBJECT IDENTIFIER
    ::= { cevChassis 974 }

-- Catalyst 2960S 24 Gig Downlinks and 2 SFP uplink, Nonstackable module

cevChassisWsC2960s48fpdL  OBJECT IDENTIFIER
    ::= { cevChassis 975 }

-- Catalyst 2960S 48 Gig Downlinks and 4 SFP uplink with support for a 2 x 10G stacking module. POE support for 740W

cevChassisWsC2960s48lpdL  OBJECT IDENTIFIER
    ::= { cevChassis 976 }

-- Catalyst 2960S 48 Gig Downlinks and 2 SFP+ uplink with support for a 2 x 10G stacking module. POE support for 370W

cevChassisWsC2960s48tdL  OBJECT IDENTIFIER
    ::= { cevChassis 977 }

-- Catalyst 2960S 48 Gig Downlinks and 2 SFP+ uplink with support for a 2 x 10G stacking module

cevChassisWsC2960s24pdL  OBJECT IDENTIFIER
    ::= { cevChassis 978 }

-- Catalyst 2960S 24 Gig Downlinks and 2 SFP+ uplink with support for a 2 x 10G stacking module. POE support for 370W

cevChassisWsC2960s24tdL  OBJECT IDENTIFIER
    ::= { cevChassis 979 }

-- Catalyst 2960S 24 Gig Downlinks and 2 SFP+ uplink with support for a 2 x 10G stacking module

cevChassisWsC2960s48fpsL  OBJECT IDENTIFIER
    ::= { cevChassis 980 }

-- Catalyst 2960S 48 Gig Downlinks and 4 SFP uplink with support for a 2 x 10G stacking module. POE support for 740W

cevChassisWsC2960s48lpsL  OBJECT IDENTIFIER
    ::= { cevChassis 981 }

-- Catalyst 2960S 48 Gig Downlinks and 4 SFP uplink with support for a 2 x 10G stacking module. POE support for 370W

cevChassisWsC2960s24psL  OBJECT IDENTIFIER
    ::= { cevChassis 982 }

-- Catalyst 2960S 24 GigDownlinks and 4 SFP uplink with support for a 2 x 10G stacking module. POE support for 370W

cevChassisWsC2960s48tsL  OBJECT IDENTIFIER
    ::= { cevChassis 983 }

-- Catalyst 2960S 48 Gig Downlinks and 4 SFP uplink with support for a 2 x 10G stacking module

cevChassisWsC2960S24tsL  OBJECT IDENTIFIER
    ::= { cevChassis 984 }

-- Catalyst 2960S 24 Gig Downlinks and 4 SFP uplink with support for a 2 x 10G stacking module

cevChassis1906Ck9  OBJECT IDENTIFIER
    ::= { cevChassis 985 }

-- 1906C/K9 Chassis (2 GE, Serial 1T, 1 EHWIC)

cevChassisAIRAP1042  OBJECT IDENTIFIER
    ::= { cevChassis 986 }

-- Cisco Aironet 1040 series WLAN Access Point with one 10/100/1000TX port and dual IEEE 802.11n radio ports

cevChassisAIRAP1041  OBJECT IDENTIFIER
    ::= { cevChassis 987 }

-- Cisco Aironet 1040 series WLAN Access Point with one 10/100/1000TX port and single IEEE 802.11n radio ports

cevChassis887Va  OBJECT IDENTIFIER
    ::= { cevChassis 988 }

-- c887-v2 with 1 VDSL/ADSL over POTS, 4 switch ports, 1 USB 1.1 port, 1 Console/Aux port, 1 ISDN and an optional Wireless LAN

cevChassis886Va  OBJECT IDENTIFIER
    ::= { cevChassis 989 }

-- c886-v2 with 1 VDSL/ADSL over ISDN, 4 switch ports, 1 USB 1.1 port, 1 Console/Aux port, 1 ISDN and an optional Wireless LAN

cevChassis867Va  OBJECT IDENTIFIER
    ::= { cevChassis 990 }

-- c867-v2 with 1 VDSL/ADSL over POTS, 4 switch ports, 1 USB 1.1 port, 1 Console/Aux port, 1 ISDN and an optional Wireless LAN

cevChassis887VaM  OBJECT IDENTIFIER
    ::= { cevChassis 991 }

-- c887m-v2 AnnexM with 1 VDSL/ADSL over POTS, 4 switch ports, 1 USB 1.1 port, 1 Console/Aux port, 1 ISDN and an optional Wireless LAN

cevChassisASR1001IDC2pOc3Pos  OBJECT IDENTIFIER
    ::= { cevChassis 992 }

-- ASR1001 chassis with 2xOc3Pos Integrated Daughter Card

cevChassisASR1001IDC4pT3  OBJECT IDENTIFIER
    ::= { cevChassis 993 }

-- ASR1001 chassis with 4xT3 Integrated Daughter Card

cevChassisASR1001IDC4pGE  OBJECT IDENTIFIER
    ::= { cevChassis 994 }

-- ASR1000 1RU chassis with 4xGe Integrated Daughter Card

cevChassisASR1001IDC8pCT1E1  OBJECT IDENTIFIER
    ::= { cevChassis 995 }

-- ASR1000 1RU chassis with 8xChT1/E1 Integrated Daughter Card

cevChassisASR1001IDCHDD  OBJECT IDENTIFIER
    ::= { cevChassis 996 }

-- ASR1000 1RU chassis with harddisk Integrated Daughter Card

cevChassisCat2960cPD8TT  OBJECT IDENTIFIER
    ::= { cevChassis 997 }

-- Catalyst 2960c 8 10/100 ports + 2 Gigabit Ethernet PD ports fixed configuration Layer 2 Ethernet Switch

cevChassisCGS252024TC  OBJECT IDENTIFIER
    ::= { cevChassis 998 }

-- Cisco Connected Grid 2520 Switch, 24 10/100 + 2 T/SFP

cevChassisCGS252016S8PC  OBJECT IDENTIFIER
    ::= { cevChassis 999 }

-- Cisco Connected Grid 2520 Switch, 16 100 SFP + 8 10/100 + 2 T/SFP

cevChassisWsC236048TdS  OBJECT IDENTIFIER
    ::= { cevChassis 1002 }

-- Catalyst 2360 Top Of Rack 48 GigE, 4 x 10G SFP+ LAN Lite

cevChassisN2kC2232TT10GE  OBJECT IDENTIFIER
    ::= { cevChassis 1003 }

-- Nexus 2000 Series 10GE Fabric Extender, 2 Power Supplies, 1 Fan Module, 32x10G-Base-T + 8x10G-BaseT Module

cevChassisN2kC2232TP10GE  OBJECT IDENTIFIER
    ::= { cevChassis 1004 }

-- Nexus 2000 Series 10GE Fabric Extender, 2 Power Supplies, 1 Fan Module, 32x10G-BaseT + 8x10GE Module

cevChassisN2kC2248TT1GE  OBJECT IDENTIFIER
    ::= { cevChassis 1005 }

-- Nexus 2000 Series 1GE Fabric Extender, 2 Power Supplies, 1 Fan Module, 48x1G-BaseT + 4x10G-BaseT Module

cevChassisN2kC2224TP1GE  OBJECT IDENTIFIER
    ::= { cevChassis 1006 }

-- Nexus 2000 Series 1GE Fabric Extender, 2 Power Supplies, 1 Fan Module, 24x100/1000-BaseT + 2xSFP+10GE

cevChassisCDScde250  OBJECT IDENTIFIER
    ::= { cevChassis 1007 }

-- Cisco Content Delivery System Model CDE-250

cevChassisN5kC5548p  OBJECT IDENTIFIER
    ::= { cevChassis 1008 }

-- Nexus 5548 Switch with 2 Power Supplies, 2 Fan Modules, 32 Ethernet/FCoE ports and 1 module

cevChassis881G2  OBJECT IDENTIFIER
    ::= { cevChassis 1009 }

-- c881G with 1 FE, 4 switch ports, 1 USB 2.0 port, 1 Console/Aux port, 1 embedded PCIe 3G modem

cevChassisWsC3750v224fsS  OBJECT IDENTIFIER
    ::= { cevChassis 1010 }

-- Catalyst 3750 24FS: 24 10/100 ports + 2 Ethernet Gigabit SFP ports fixed configuration Layer 2/Layer 3 Ethernet Stackable switch

cevChassisOeVWaas  OBJECT IDENTIFIER
    ::= { cevChassis 1011 }

-- Cisco Optimization Engine Virtual Wide Area Application Services

cevChassisCrs16SB  OBJECT IDENTIFIER
    ::= { cevChassis 1012 }

-- Enhanced CRS 16 slots Line Card Chassis

cevChassisCat2960cG8TC  OBJECT IDENTIFIER
    ::= { cevChassis 1014 }

-- Catalyst 2960c 8 10/100/1000 ports + 2 dual purpose Gigabit Ethernet ports module

cevChassisECDS1100  OBJECT IDENTIFIER
    ::= { cevChassis 1017 }

-- Cisco Enterprise Content Delivery System Model ECDS-1100

cevChassisECDS3100  OBJECT IDENTIFIER
    ::= { cevChassis 1018 }

-- Cisco Enterprise Content Delivery System Model ECDS-3100

cevChassisIE301016S8PC  OBJECT IDENTIFIER
    ::= { cevChassis 1019 }

-- Cisco Industrial Ethernet 3010 Switch, 16 100 SFP + 8 10/100 + 2 T/SFP

cevChassisIE301024TC  OBJECT IDENTIFIER
    ::= { cevChassis 1020 }

-- Cisco Industrial Ethernet 3010 Switch, 24 10/100 + 2 T/SFP

cevChassisWsC4948ef10GE  OBJECT IDENTIFIER
    ::= { cevChassis 1023 }

-- Catalyst 4900 series front exhaust fixed configuration switch with 48 10/100/1000BaseT ports and four 10Gbps/1Gbps SFP+/SFP ports(WS-C4948E-F)

cevChassisWave284K9  OBJECT IDENTIFIER
    ::= { cevChassis 1024 }

-- Cisco Wide Area Virtualization Engine 284

cevChassisWave584K9  OBJECT IDENTIFIER
    ::= { cevChassis 1025 }

-- Cisco Wide Area Virtualization Engine 584

cevChassisWave684K9  OBJECT IDENTIFIER
    ::= { cevChassis 1026 }

-- Cisco Wide Area Virtualization Engine 684

cevChassisWave7441K9  OBJECT IDENTIFIER
    ::= { cevChassis 1027 }

-- Cisco Wide Area Virtualization Engine 7441

cevChassisWave7471K9  OBJECT IDENTIFIER
    ::= { cevChassis 1028 }

-- Cisco Wide Area Virtualization Engine 7471

cevChassisWave7626K9  OBJECT IDENTIFIER
    ::= { cevChassis 1029 }

-- Cisco Wide Area Virtualization Engine 7626

cevChassisCat292848TCC  OBJECT IDENTIFIER
    ::= { cevChassis 1032 }

-- Catalyst 48 10/100 ports + 2 10/100/1000 Ethernet ports fixed configuration Layer 2 Ethernet switch

cevChassisCat292824TCC  OBJECT IDENTIFIER
    ::= { cevChassis 1033 }

-- Catalyst 24 10/100 ports + 2 10/100/1000 Ethernet ports fixed configuration Layer 2 Ethernet switch

cevChassisCat292824LTC  OBJECT IDENTIFIER
    ::= { cevChassis 1034 }

-- Catalyst 2928 24 10/100 ports + 2 10/100/1000 Ethernet ports fixed configuration Layer 2 Ethernet switch POE support for 123 W

cevChassisGrwicDes2s8pc  OBJECT IDENTIFIER
    ::= { cevChassis 1036 }

-- Grid Router Switching Module with 2 GE(1 combo, 1 SFP) interfaces and 8 100BaseT interfaces supporting PoE

cevChassisGrwicDes6s  OBJECT IDENTIFIER
    ::= { cevChassis 1037 }

-- Grid Router Switching Module with 2 GE(1 combo, 1 SFP) interfaces and 4 100FX interfaces

cevChassisN5kC5596Up  OBJECT IDENTIFIER
    ::= { cevChassis 1038 }

-- Nexus 5596 Switch with 2 Power Supplies, 4 Fan Modules and 48 Ethernet/FCoE ports

cevChassisC1861eUc2BriK9  OBJECT IDENTIFIER
    ::= { cevChassis 1039 }

-- C1861E UC with support for 2 BRI ports and CUE

cevChassisC1861eUc4FxoK9  OBJECT IDENTIFIER
    ::= { cevChassis 1040 }

-- C1861E UC with support for 4 FXO ports and CUE

cevChassisC1861eSrstFK9  OBJECT IDENTIFIER
    ::= { cevChassis 1041 }

-- C1861E SRST with support for 4 FXO ports

cevChassisC1861eSrstBK9  OBJECT IDENTIFIER
    ::= { cevChassis 1042 }

-- C1861E SRST with support for 2 BRI ports

cevChassisC1861eSrstCFK9  OBJECT IDENTIFIER
    ::= { cevChassis 1043 }

-- C1861E SRST with support for 4 FXO ports and CUE

cevChassisC1861eSrstCBK9  OBJECT IDENTIFIER
    ::= { cevChassis 1044 }

-- C1861E SRST with support for 4 BRI ports and CUE

cevChassis88XG2DSL  OBJECT IDENTIFIER
    ::= { cevChassis 1045 }

-- c88XG with 1 xDSL, 1 FE, 4 switch ports, 1 USB 2.0 port, 1 Console/Aux port, 1 embedded PCIe 3G modem

cevChassisWave8541  OBJECT IDENTIFIER
    ::= { cevChassis 1047 }

-- Cisco Wide Area Virualization Engine Model 8541

cevChassisWave7571  OBJECT IDENTIFIER
    ::= { cevChassis 1048 }

-- Cisco Wide Area Virtualization Engine Model 7571

cevChassisWave7541  OBJECT IDENTIFIER
    ::= { cevChassis 1049 }

-- Cisco Wide Area Virtualization Engine Model 7541

cevChassisWave694  OBJECT IDENTIFIER
    ::= { cevChassis 1050 }

-- Cisco Wide Area Virtualization Engine Model 694

cevChassisWave594  OBJECT IDENTIFIER
    ::= { cevChassis 1051 }

-- Cisco Wide Area Virtualization Engine Model 594

cevChassisWave294  OBJECT IDENTIFIER
    ::= { cevChassis 1052 }

-- Cisco Wide Area Virtualization Engine Model 294

cevChassis5915  OBJECT IDENTIFIER
    ::= { cevChassis 1053 }

-- Chassis Type for 5915 Embedded Services Router

cevChassis86xVAE  OBJECT IDENTIFIER
    ::= { cevChassis 1055 }

-- Chassis for Cisco 86xVAE series products

cevChassisAp802gn  OBJECT IDENTIFIER
    ::= { cevChassis 1056 }

-- Cisco AP802 Access Point with single IEEE 802.11g/n radio port

cevChassisN2kB22HPP  OBJECT IDENTIFIER
    ::= { cevChassis 1058 }

-- N2K 10GE Fabric Extender, 16xSFP+ 10GE and 8xSFP+ 10GE (req SFP+ optics) for HP c-class Blade chassis

cevChassisN2kC2248GVP  OBJECT IDENTIFIER
    ::= { cevChassis 1059 }

-- Nexus 2000 Series 1 GE Fabric Extender, 1 Power Supply, 2 Fans, 48x100/1000 PoE+ ports  +  4x10GE (req SFP+)

cevChassisN3kC3064PQ  OBJECT IDENTIFIER
    ::= { cevChassis 1060 }

-- Nexus 3000 Series 1 RU fixed chassis with 48 SFP+ and 4 QSFP ports, 2 Power Supplies and 1 Fan tray

cevChassisN2kC2232TM10GE  OBJECT IDENTIFIER
    ::= { cevChassis 1061 }

-- Nexus 2000 Series 10GE Fabric Extender, 2 Power Supplies, 1 Fan Module, 32x10G-BaseT + field upgradeable module

cevChassisUCSFI6248UP  OBJECT IDENTIFIER
    ::= { cevChassis 1062 }

-- Cisco UCS Unified Computing System 6248UP 48-Unified Port Fabric Interconnect

cevChassisUCSFI6296UP  OBJECT IDENTIFIER
    ::= { cevChassis 1063 }

-- Cisco UCS Unified Computing System 6296UP 96-Unified Port Fabric Interconnect

cevChassis2811ve  OBJECT IDENTIFIER
    ::= { cevChassis 1064 }

-- 2811ve router with two integrated fast ethernets and integrated VPN

cevChassis1841ve  OBJECT IDENTIFIER
    ::= { cevChassis 1065 }

-- 1841ve data only router with 2 HWIC slot

cevChassis2960c8tcS  OBJECT IDENTIFIER
    ::= { cevChassis 1066 }

-- Catalyst 2960C 8 10/100 FE ports + 2 Gig Dual Media Uplinks fixed configuration Layer 2 Ethernet switch, lanlite only Chassis

cevChassis2960c8tcL  OBJECT IDENTIFIER
    ::= { cevChassis 1067 }

-- Catalyst 2960C 8 10/100 FE ports + 2 Gig Dual Media Uplinks fixed configuration Layer 2 Ethernet switch Chassis

cevChassis2960c8pcL  OBJECT IDENTIFIER
    ::= { cevChassis 1068 }

-- Catalyst 2960C 8 10/100 FE with PoE + 2 Gig Dual Media Uplinks fixed configuration Layer 2 Ethernet switch Chassis

cevChassis2960c12pcL  OBJECT IDENTIFIER
    ::= { cevChassis 1069 }

-- Catalyst 2960C 12 10/100 FE with POE + 2 Gig Dual Media Uplinks fixed configuration Layer 2 Ethernet switch Chassis

cevChassis3560cpd8ptS  OBJECT IDENTIFIER
    ::= { cevChassis 1070 }

-- Catalyst 3560C 8 10/100/1000 with PoE and 2 Gig Copper PoE+ Uplinks fixed configuration Layer 2/Layer 3 Ethernet switch Chassis

cevChassis886Vag7K9  OBJECT IDENTIFIER
    ::= { cevChassis 1071 }

-- C886G w/ 1 WAN VDSL2/ADSL2+ over ISDN, 4 switch ports, 1 embedded Global 3G HSPA+ modem with GPS and SMS

cevChassis887VagSK9  OBJECT IDENTIFIER
    ::= { cevChassis 1072 }

-- C887G w/ 1 WAN VDSL2/ADSL2+ over POTS, 4 switch ports, 1 embedded Sprint 3G EVDO modem with GPS and SMS

cevChassis887Vag7K9  OBJECT IDENTIFIER
    ::= { cevChassis 1073 }

-- C887G w/ 1 WAN VDSL2/ADSL2+ over POTS, 4 switch ports, 1 embedded Global 3G HSPA+ modem with GPS and SMS

cevChassis887Vamg7K9  OBJECT IDENTIFIER
    ::= { cevChassis 1074 }

-- C887G w/ 1 WAN VDSL2/ADSL2+ over POTS (Annex M), 4 switch ports, 1 embedded Global 3G HSPA+ modem with GPS and SMS

cevChassis888Eg7K9  OBJECT IDENTIFIER
    ::= { cevChassis 1075 }

-- C888EG w/ 1 WAN G.SHDSL (EFM), 4 switch ports, 1 embedded Global 3G HSPA+ modem with GPS and SMS

cevChassis881GUK9  OBJECT IDENTIFIER
    ::= { cevChassis 1076 }

-- C881G w/ 1 WAN FE, 4 switch ports, 1 embedded Global 3G HSPA modem with GPS and SMS

cevChassis881GSK9  OBJECT IDENTIFIER
    ::= { cevChassis 1077 }

-- C881G w/ 1 WAN FE, 4 switch ports, 1 embedded Sprint 3G EVDO Rev A modem with GPS and SMS

cevChassis881GVK9  OBJECT IDENTIFIER
    ::= { cevChassis 1078 }

-- C881G w/ 1 WAN FE, 4 switch ports, 1 embedded Verizon 3G EVDO Rev A modem with GPS and SMS

cevChassis881GBK9  OBJECT IDENTIFIER
    ::= { cevChassis 1079 }

-- C881G w/ 1 WAN FE, 4 switch ports, 1 embedded BSNL 3G EVDO Rev A modem with GPS and SMS

cevChassis881G7K9  OBJECT IDENTIFIER
    ::= { cevChassis 1080 }

-- C881G w/ 1 WAN FE, 4 switch ports, 1 embedded Global 3G HSPA+ modem with GPS and SMS

cevChassis881G7AK9  OBJECT IDENTIFIER
    ::= { cevChassis 1081 }

-- C881G w/ 1 WAN FE, 4 switch ports, 1 embedded ATT 3G HSPA+ modem with GPS and SMS

cevChassisN5kC5548UP  OBJECT IDENTIFIER
    ::= { cevChassis 1084 }

-- Nexus 5548 Switch with 2 Power Supplies, 2 Fan Modules, 32 Ethernet/FC (Unified) ports and 1 module

cevChassis881W  OBJECT IDENTIFIER
    ::= { cevChassis 1085 }

-- C881W Router series with 1 Fast Ethernet WAN, 4 Fast Ethernet LAN with 2 PoE, Wireless LAN, 1 USB 2.0 port, 1 Console/Aux port, 256MB flash memory and 512MB DRAM

cevChassis886VAW  OBJECT IDENTIFIER
    ::= { cevChassis 1086 }

-- C886VA-W Router series with 1 ADSL2/2+ Annex B, 1 ISDN,  4 Fast Ethernet LAN with 2 PoE, Wireless LAN, 1 USB 2.0 port, 1 Console/Aux port, 256MB flash memory and 512MB DRAM

cevChassis887VAMW  OBJECT IDENTIFIER
    ::= { cevChassis 1087 }

-- C887VAM-W Router series with 1 ADSL2/2+ Annex M, 4 Fast Ethernet LAN with 2 PoE, Wireless LAN, 1 USB 2.0 port, 1 Console/Aux port, 256MB flash memory and 512MB DRAM

cevChassis887VAW  OBJECT IDENTIFIER
    ::= { cevChassis 1088 }

-- C887VA-W Router series with 1 VDSL, 4 Fast Ethernet LAN with 2 PoE, Wireless LAN, 1 USB 2.0 port, 1 Console/Aux port, 256MB flash memory and 512MB DRAM

cevChassis819G  OBJECT IDENTIFIER
    ::= { cevChassis 1089 }

-- C819G Router series with 1 Gigabit Ethernet WAN, 4 Fast Ethernet LAN, 1 3G WAN, 1 Serial, 1 Console/Aux ports, 256MB flash memory and 512MB DRAM

cevChassis819HG  OBJECT IDENTIFIER
    ::= { cevChassis 1090 }

-- C819HG Hardened Router series with 1 Gigabit Ethernet WAN, 4 Fast Ethernet LAN, 1 3G WAN, 1 Serial, 1 Console/Aux ports, 256MB flash memory, 512MB DRAM

cevChassisIAD886VA  OBJECT IDENTIFIER
    ::= { cevChassis 1091 }

-- iad886-v2 with 1 VDSL/ADSL over ISDN, 4 switch ports, 1 USB 1.1 port, 1 Console/Aux port, 1 ISDN and an optional Wireless LAN

cevChassisIAD886VAJ  OBJECT IDENTIFIER
    ::= { cevChassis 1092 }

-- iad886j-v2 Annex J with 1 VDSL/ADSL over ISDN, 4 switch ports, 1 USB 1.1 port, 1 Console/Aux port, 1 ISDN and an optional Wireless LAN

cevChassisIAD887VA  OBJECT IDENTIFIER
    ::= { cevChassis 1093 }

-- iad887-v2 with 1 VDSL/ADSL over POTS, 4 switch ports, 1 USB 1.1 port, 1 Console/Aux port, 1 ISDN and an optional Wireless LAN

cevChassisIAD887VAM  OBJECT IDENTIFIER
    ::= { cevChassis 1094 }

-- iad887m-v2 AnnexM with 1 VDSL/ADSL over POTS, 4 switch ports, 1 USB 1.1 port, 1 Console/Aux port, 1 ISDN and an optional Wireless LAN

cevChassisPCM  OBJECT IDENTIFIER
    ::= { cevChassis 1095 }

-- Cisco Prime Collaboration Manager Module

cevChassisDSavsm  OBJECT IDENTIFIER
    ::= { cevChassis 1102 }

-- Cisco Content Delivery System Model AVSM

cevChassisEcdsVB  OBJECT IDENTIFIER
    ::= { cevChassis 1104 }

-- Cisco Media Delivery Engine

cevChassisN3kC3064PQ10GE  OBJECT IDENTIFIER
    ::= { cevChassis 1105 }

-- Nexus 3000 Series 1 RU fixed chassis (Trident+) with 48 SFP+ and 4 QSFP ports, no power supply, no fan

cevChassisN3kC3048TP1GE  OBJECT IDENTIFIER
    ::= { cevChassis 1106 }

-- Nexus 3000 Series 1 RU fixed chassis with 48x1G-BaseT and 4x10GE SFP+ ports, no Power Supply, no fan

cevChassisN3kC3016Q40GE  OBJECT IDENTIFIER
    ::= { cevChassis 1107 }

-- Nexus 3000 Series 1 RU fixed chassis with 16x40GE QSFP ports, no Power Supply, no fan

cevChassisASR903  OBJECT IDENTIFIER
    ::= { cevChassis 1118 }

-- Cisco Aggregation Services Router 900 Series, 3RU Chassis

cevChassis3560c12pcS  OBJECT IDENTIFIER
    ::= { cevChassis 1121 }

-- Catalyst 3560C 12 10/100 with PoE + 2 Gig Dual Media Uplinks fixed configuration Layer 2/Layer 3 Ethernet switch chassis

cevChassis3560c8pcS  OBJECT IDENTIFIER
    ::= { cevChassis 1122 }

-- Catalyst 3560C 8 10/100 with PoE + 2 Gig Dual Media Uplinks fixed configuration Layer 2/Layer 3 Ethernet switch chassis

cevChassisCrs8SB  OBJECT IDENTIFIER
    ::= { cevChassis 1123 }

-- CRS-8 Line Card Chassis-enhanced for CRS-8/S-B

cevChassisASR5000CHSSYSK9  OBJECT IDENTIFIER
    ::= { cevChassis 1145 }

-- Individually orderable base chassis

cevChassisASR55CHSSYS  OBJECT IDENTIFIER
    ::= { cevChassis 1146 }

-- ASR5500 Base Chassis, with MidPlane EEProm Card (MEC, ASR55-MEC)

cevChassisN7Kc7004  OBJECT IDENTIFIER
    ::= { cevChassis 1147 }

-- Nexus7000 4slot zonda n7k chassis N7K-C7004

cevChassisASR901  OBJECT IDENTIFIER
    ::= { cevChassis 1159 }

-- Pura-C platform

cevChassisASR901E  OBJECT IDENTIFIER
    ::= { cevChassis 1160 }

-- Pura-E platform

cevChassisOeSmSre710  OBJECT IDENTIFIER
    ::= { cevChassis 1161 }

-- Cisco Optimization Engine Service Module Service Ready Engine 710

cevChassisOeSmSre910  OBJECT IDENTIFIER
    ::= { cevChassis 1162 }

-- Cisco Optimization Engine Service Module Service Ready Engine 910

cevChassisN3kC3064PQ10GX  OBJECT IDENTIFIER
    ::= { cevChassis 1163 }

-- Nexus 3000 Series 1 RU fixed chassis (Trident+) with  48 SFP+ and 4 QSFP ports, no power supply, no fan

cevChassisVSR1000  OBJECT IDENTIFIER
    ::= { cevChassis 1165 }

-- Cisco Virtual Services Router 1000 Chassis

cevChassisFlowAgent3000  OBJECT IDENTIFIER
    ::= { cevChassis 1166 }

-- Cisco Integrated NetFlow Generation Agent

cevChassisASR1002X  OBJECT IDENTIFIER
    ::= { cevChassis 1167 }

-- Cisco Aggregation Services Router 1000 Series, ASR1002-X Chassis

cevChassisNamApp2304  OBJECT IDENTIFIER
    ::= { cevChassis 1168 }

-- Cisco NAM Appliance 2304

cevChassisNamApp2320  OBJECT IDENTIFIER
    ::= { cevChassis 1169 }

-- Cisco NAM Appliance 2320

cevChassisECDS50IVB  OBJECT IDENTIFIER
    ::= { cevChassis 1173 }

-- Cisco Enterprise Content Delivery System Model MDE50IVB

cevChassisN5kC5596TFA  OBJECT IDENTIFIER
    ::= { cevChassis 1175 }

-- Nexus 5596 Switch with 2 Power Supplies, 4 Fan Modules and 48x 10G BaseT Ethernet/FCoE ports

cevChassisASR9001  OBJECT IDENTIFIER
    ::= { cevChassis 1178 }

-- Cisco Aggregation Services Router (ASR) 9001 Chassis

cevChassis819GM  OBJECT IDENTIFIER
    ::= { cevChassis 1188 }

-- C819GM Router series with 1 Gigabit Ethernet WAN, 4 Fast Ethernet LAN, 1 3G WAN, 1 Serial, 1 Console/Aux ports, 1GB flash memory and 1GB DRAM

cevChassis819HGM  OBJECT IDENTIFIER
    ::= { cevChassis 1189 }

-- C819HGM Hardened Router series with 1 Gigabit Ethernet WAN, 4 Fast Ethernet LAN, 1 3G WAN, 1 Serial, 1 Console/Aux ports, 1GB flash memory and 1GB DRAM

cevChassisN2kC2232TME10GE  OBJECT IDENTIFIER
    ::= { cevChassis 1190 }

-- Nexus 2000 Series 10GE Fabric Extender, 2 Power Supplies, 1 Fan Module, 32x10G-BaseT + field upgradeable module

cevChassisCDScde2502s6  OBJECT IDENTIFIER
    ::= { cevChassis 1191 }

-- Cisco Content Delivery System Model CDE-250-2S6

cevChassisCDScde2502m0  OBJECT IDENTIFIER
    ::= { cevChassis 1192 }

-- Cisco Content Delivery System Model CDE-250-2M0

cevChassisCDScde2502s8  OBJECT IDENTIFIER
    ::= { cevChassis 1193 }

-- Cisco Content Delivery System Model CDE-250-2S8

cevChassisASA1000V  OBJECT IDENTIFIER
    ::= { cevChassis 1194 }

-- Adaptive Security Appliance (ASA) 1000V Cloud Firewall for the Nexus 1000V chassis

cevChassisISR4400  OBJECT IDENTIFIER
    ::= { cevChassis 1195 }

-- Cisco ISR 4400 Series Chassis

cevChassisMe3600x24CxM  OBJECT IDENTIFIER
    ::= { cevChassis 1196 }

-- Cisco ME 3600X Ethernet Access Switch, 16 GE SFP ports + 8 RJ45/SFP combo ports + 4 10Gbps XFP ports + 16 T1/E1 + 4 OC3 ports, Layer 2/3 Carrier Ethernet Switch Router

cevChassisA9014CFD  OBJECT IDENTIFIER
    ::= { cevChassis 1197 }

-- A new Chassis PID for Ethernet only chassis (with Port based feature)

cevChassisA9014CFtD  OBJECT IDENTIFIER
    ::= { cevChassis 1198 }

-- A new Chassis PID  for Ethernet + TDM chassis( with Port based Feature)

cevChassisMDE10XVB  OBJECT IDENTIFIER
    ::= { cevChassis 1199 }

-- Cisco Enterprise Content Delivery System Model MDE10XVB

cevChassisWsC4500x16  OBJECT IDENTIFIER
    ::= { cevChassis 1202 }

-- Cisco Catalyst 4500X series fixed 10GE aggregation switch with 16 10GE SFP+ ports

cevChassisWsC4500x32  OBJECT IDENTIFIER
    ::= { cevChassis 1203 }

-- Cisco Catalyst 4500X series fixed 10GE aggregation switch with 32 10GE SFP+ ports

cevChassisN2kC2248PQ10GE  OBJECT IDENTIFIER
    ::= { cevChassis 1205 }

-- N2K 10GE Fabric Extender, 2PS, 4 Fan Module, 48xSFP+ 1/10GE + 4xQSFP  (requires QSFP with 10GE splitters)

cevChassisCDScde2502s9  OBJECT IDENTIFIER
    ::= { cevChassis 1206 }

-- Cisco Content Delivery System Model CDE-250-2S9

cevChassisCDScde2502s10  OBJECT IDENTIFIER
    ::= { cevChassis 1207 }

-- Cisco Content Delivery System Model CDE-250-2S10

cevChassisCDScdeGeneric  OBJECT IDENTIFIER
    ::= { cevChassis 1208 }

-- Cisco Content Delivery System Generic Hardware

cevChassisN2kB22FTSP  OBJECT IDENTIFIER
    ::= { cevChassis 1210 }

-- N2K 10GE Fabric Extender, 16xSFP+ 10GE and 8xSFP+ 10GE (req SFP+ optics) for Fujitsu PRIMERGY BX900

cevChassisN2kB22DELLP  OBJECT IDENTIFIER
    ::= { cevChassis 1211 }

-- N2K 10GE Fabric Extender, 16xSFP+ 10GE and 8xSFP+ 10GE (req SFP+ optics) for Dell M1000E

cevChassisASR9922Dc  OBJECT IDENTIFIER
    ::= { cevChassis 1225 }

-- ASR 9922 20 Line Card Slot DC Chassis w/ PEM V2

cevChassisASR9922Ac  OBJECT IDENTIFIER
    ::= { cevChassis 1226 }

-- ASR 9922 20 Line Card Slot AC Chassis w/ PEM V2

cevChassisN6kC600496Q  OBJECT IDENTIFIER
    ::= { cevChassis 1237 }

-- Nexus 6004 Switch with 2 Power Supplies, 4 Fan Modules and 48Q 40GE Ethernet/FCoE ports

cevChassisN3kC3548P10G  OBJECT IDENTIFIER
    ::= { cevChassis 1238 }

-- Nexus 3500 Series 1 RU fixed chassis with 48 SFPs, 2 Power Supplies, 4 Individual Fans

cevChassisN3kC3064TQ10GT  OBJECT IDENTIFIER
    ::= { cevChassis 1239 }

-- Nexus 3000 Series 1 RU fixed chassis (Trident+) with  48 SFP+ and 4 QSFP ports, no power supply, no fan

cevChassis86xVAEW  OBJECT IDENTIFIER
    ::= { cevChassis 1240 }

-- Chassis for Cisco 86xVAEW series products

cevChassisASR9912AC  OBJECT IDENTIFIER
    ::= { cevChassis 1241 }

-- ASR 9912 10 Line Card Slot AC Chassis w/ PEM V2

cevChassisASR9912DC  OBJECT IDENTIFIER
    ::= { cevChassis 1242 }

-- ASR 9912 10 Line Card Slot DC Chassis w/ PEM V2

cevChassisOeKWaas  OBJECT IDENTIFIER
    ::= { cevChassis 1243 }

-- Cisco Optimization Engine Virtualized Wide Area Application Services instance running on the KVM hypervisor container (kWAAS)

cevChassisasr1000  OBJECT IDENTIFIER
    ::= { cevChassis 1244 }

-- asr1000 chassis

cevChassisCDScde2202s4  OBJECT IDENTIFIER
    ::= { cevChassis 1245 }

-- Cisco Content Delivery System Model CDE-220-2S4

cevChassisISR4441  OBJECT IDENTIFIER
    ::= { cevChassis 1246 }

-- Cisco ISR 4441 Router Chassis

cevChassisISR4442  OBJECT IDENTIFIER
    ::= { cevChassis 1247 }

-- Cisco ISR 4442 Router Chassis with HDD

cevChassisISR4451  OBJECT IDENTIFIER
    ::= { cevChassis 1248 }

-- Cisco ISR 4451 Router Chassis

cevChassisISR4452  OBJECT IDENTIFIER
    ::= { cevChassis 1249 }

-- Cisco ISR 4452 Router Chassis with HDD

cevChassisAIRAP1553  OBJECT IDENTIFIER
    ::= { cevChassis 1251 }

-- Cisco Aironet 1550 Series Outdoor Mesh Access Points with three IEEE 802.11n radio port

cevChassisAIRAP1552  OBJECT IDENTIFIER
    ::= { cevChassis 1252 }

-- Cisco Aironet 1550 Series Outdoor Mesh Access Points with dual IEEE 802.11n radio port

cevChassisAIRAP1602  OBJECT IDENTIFIER
    ::= { cevChassis 1253 }

-- Cisco Aironet 1600 Series WLAN Access Point with dual IEEE 802.11n radio port

cevChassisAIRAP1601  OBJECT IDENTIFIER
    ::= { cevChassis 1254 }

-- Cisco Aironet 1600 Series WLAN Access Point with single IEEE 802.11n radio port

cevChassisAIRAP2602  OBJECT IDENTIFIER
    ::= { cevChassis 1255 }

-- Cisco Aironet 2600 Series WLAN Access Point with dualIEEE 802.11n radio port

cevChassisAIRAP2601  OBJECT IDENTIFIER
    ::= { cevChassis 1256 }

-- Cisco Aironet 2600 Series WLAN Access Point with singleIEEE 802.11n radio port

cevChassisAIRAP3602  OBJECT IDENTIFIER
    ::= { cevChassis 1257 }

-- Cisco Aironet 3600 Series WLAN Access Point with one10/100/1000TX port and dual IEEE 802.11n radio port

cevChassisAIRAP3601  OBJECT IDENTIFIER
    ::= { cevChassis 1258 }

-- Cisco Aironet 3600 Series WLAN Access Point with one10/100/1000TX port and single IEEE 802.11n radio port

cevChassisWsC2960x48fpdL  OBJECT IDENTIFIER
    ::= { cevChassis 1259 }

-- Catalyst 2960X 48 Gig Downlinks, 2 SFP+ uplink, 2 x 10G stacking module, POE+ support for 740W

cevChassisWsC2960x48lpdL  OBJECT IDENTIFIER
    ::= { cevChassis 1260 }

-- Catalyst 2960X 48 Gig Downlinks, 2 SFP+ uplink, 2 x 10G stacking module, POE+ support for 370W

cevChassisWsC2960x48tdL  OBJECT IDENTIFIER
    ::= { cevChassis 1261 }

-- Catalyst 2960X 48 Gig Downlinks, 2 SFP+ uplink, 2 x 10G stacking module

cevChassisWsC2960x24pdL  OBJECT IDENTIFIER
    ::= { cevChassis 1262 }

-- Catalyst 2960X 24 Gig Downlinks, 2 SFP+ uplink, 2 x 10G stacking module, POE+ support for 370W

cevChassisWsC2960x24tdL  OBJECT IDENTIFIER
    ::= { cevChassis 1263 }

-- Catalyst 2960X 24 Gig Downlinks, 2 SFP+ uplink, 2 x 10G stacking module

cevChassisWsC2960x48fpsL  OBJECT IDENTIFIER
    ::= { cevChassis 1264 }

-- Catalyst 2960X 48 Gig Downlinks, 4 SFP uplink with support for 2 x 10G stacking module, POE+ support for 740W

cevChassisWsC2960x48lpsL  OBJECT IDENTIFIER
    ::= { cevChassis 1265 }

-- Catalyst 2960X 48 Gig Downlinks, 4 SFP uplink with support for 2 x 10G stacking module, POE+ support for 370W

cevChassisWsC2960x24psL  OBJECT IDENTIFIER
    ::= { cevChassis 1266 }

-- Catalyst 2960X 24 Gig Downlinks, 4 SFP uplink with support for  2 x 10G stacking module, POE+ support for 370W

cevChassisWsC2960x48tsL  OBJECT IDENTIFIER
    ::= { cevChassis 1267 }

-- Catalyst 2960X 48 Gig Downlinks, 4 SFP uplink with support for 2 x 10G stacking module

cevChassisWsC2960x24tsL  OBJECT IDENTIFIER
    ::= { cevChassis 1268 }

-- Catalyst 2960X 24 Gig Downlinks, 4 SFP uplink with support for 2 x 10G stacking module

cevChassisWsC2960x24pskL  OBJECT IDENTIFIER
    ::= { cevChassis 1269 }

-- Catalyst 2960X 24 Gig Downlinks, 4 SFP uplink NonStakable

cevChassisWsC2960x48lpsS  OBJECT IDENTIFIER
    ::= { cevChassis 1270 }

-- Catalyst 2960X 48 Gig Downlinks, 4 SFP uplink NonStakable, POE+ support for 370W

cevChassisWsC2960x24psS  OBJECT IDENTIFIER
    ::= { cevChassis 1271 }

-- Catalyst 2960X 24 Gig Downlinks, 2 SFP uplink Non Stackable, POE+ support for 370W

cevChassisWsC2960x48tsLL  OBJECT IDENTIFIER
    ::= { cevChassis 1272 }

-- Catalyst 2960X 48 Gig Downlinks, 2 SFP uplink Non Stackable

cevChassisWsC2960x24tsLL  OBJECT IDENTIFIER
    ::= { cevChassis 1273 }

-- Catalyst 2960X 24 Gig Downlinks, 2 SFP uplink Non Stackable

cevChassisIE200016TCGP  OBJECT IDENTIFIER
    ::= { cevChassis 1278 }

-- Cisco Base + Lite Industrial Ethernet 2000 Switch, 12 10/100 T +  2 1000 T/SFP + 4 POE

cevChassisIE200016TCGEP  OBJECT IDENTIFIER
    ::= { cevChassis 1279 }

-- Cisco Base + 1588 Industrial Ethernet 2000 Switch, 12 10/100 T +  2 1000 T/SFP + 4 POE

cevChassisIE200016TCGNXP  OBJECT IDENTIFIER
    ::= { cevChassis 1280 }

-- Cisco Base + NAT + 1588 + Conformal Coating Industrial Ethernet 2000 Switch, 12 10/100 T +  2 1000 T/SFP + 4 POE

cevChassisRAIE1783BMS12T4E2CGL  OBJECT IDENTIFIER
    ::= { cevChassis 1281 }

-- Rockwell IA Base + Lite Industrial Ethernet 2000 Switch, 12 10/100 T + 2 1000 T/SFP + 4 POE

cevChassisRAIE1783BMS12T4E2CGP  OBJECT IDENTIFIER
    ::= { cevChassis 1282 }

-- Rockwell IA Base + 1588 Industrial Ethernet 2000 Switch, 12 10/100 T + 2 1000 T/SFP + 4 POE

cevChassisRAIE1783BMS12T4E2CGNK  OBJECT IDENTIFIER
    ::= { cevChassis 1283 }

-- Rockwell IA Base + NAT + 1588 + Conformal Coating  Industrial Ethernet 2000 Switch, 12 10/100 T + 2 1000 T/SFP + 4 POE

cevChassisIE20008TCGN  OBJECT IDENTIFIER
    ::= { cevChassis 1284 }

-- Cisco Industrial Ethernet 2000 Switch+1588+NAT, 8 10/100 T + 2 1000 T/SFP, contact prashrof

cevChassisIE200016TCGN  OBJECT IDENTIFIER
    ::= { cevChassis 1285 }

-- Cisco Industrial Ethernet 2000 Switch+1588+NAT, 16 10/100 T + 2 100 T + 2 1000 T/SFP, contact prashrof

cevChassisRAIE1783BMS10CGN  OBJECT IDENTIFIER
    ::= { cevChassis 1286 }

-- Rockwell Industrial Ethernet 2000 Switch+1588+NAT, 8 10/100 T + 2 1000 T/SFP, contact prashrof

cevChassisRAIE1783BMS20CGN  OBJECT IDENTIFIER
    ::= { cevChassis 1287 }

-- Rockwell Industrial Ethernet 2000 Switch+1588+NAT, 16 10/100 T + 2 1000 T/SFP, contact prashrof

cevChassisNexus1010X  OBJECT IDENTIFIER
    ::= { cevChassis 1288 }

-- Large Virtual service Appliance

cevChassisNexus1110S  OBJECT IDENTIFIER
    ::= { cevChassis 1289 }

-- Gen-2 Base  Virtual service Appliance

cevChassisNexus1110XL  OBJECT IDENTIFIER
    ::= { cevChassis 1290 }

-- Gen-2 Extra Large  Virtual service Appliance

cevChassisNexus1110X  OBJECT IDENTIFIER
    ::= { cevChassis 1291 }

-- Gen-2 Large  Virtual service Appliance

cevChassisNexus1000VKVM  OBJECT IDENTIFIER
    ::= { cevChassis 1292 }

-- Nexus 1000V on KVM hypervisor

cevChassisNexus1000VMH  OBJECT IDENTIFIER
    ::= { cevChassis 1294 }

-- Nexus1000V on Microsoft Hypervisor

cevChassisVG202XM  OBJECT IDENTIFIER
    ::= { cevChassis 1295 }

-- Line side Analog Gateway VG202XM with 2FXS Analog ports

cevChassisVG204XM  OBJECT IDENTIFIER
    ::= { cevChassis 1296 }

-- Line side Analog Gateway VG204XM with 4FXS Analog ports

cevChassisME2600X  OBJECT IDENTIFIER
    ::= { cevChassis 1303 }

-- Cisco ME 2600X Series Ethernet Access Switches is Cisco's switches built specifically for the Fiber to the Home/Premise (FTTH/FTTP) services with 10G capability. It is 1-rack-unit (1RU), fixed-form-factor platform hardware-optimized for ANSI,ETSI & AC Power configurations

cevChassisNCSCHASSIS  OBJECT IDENTIFIER
    ::= { cevChassis 1304 }

-- NCS 6008 - 8-Slot Chassis

cevChassisN6kC600164P  OBJECT IDENTIFIER
    ::= { cevChassis 1308 }

-- Nexus 6001 chassis

cevChassis131WsC385024U  OBJECT IDENTIFIER
    ::= { cevChassis 1309 }

-- cisco Catalyst 3850 24 Port UPOE

cevChassis131WsC385048U  OBJECT IDENTIFIER
    ::= { cevChassis 1310 }

-- cisco Catalyst 3850 48 Port UPOE

cevChassisDSC9250IK9  OBJECT IDENTIFIER
    ::= { cevChassis 1326 }

-- DS-C9250I-K9, Chassis for MDS 9250i Intelligent Fabric Switch, 40FC+8FCoE+2FCIP

cevChassisDSC9710  OBJECT IDENTIFIER
    ::= { cevChassis 1327 }

-- DS-C9710, Chassis for MDS 10-Slot Director Switch

cevChassisN2kB22IBMP  OBJECT IDENTIFIER
    ::= { cevChassis 1339 }

-- N2K-B22IBM-P is a 10G Fabric Extender with 14 10G KR HIF ports and 8 NIF (uplink) ports

cevChassisN6kC600164T  OBJECT IDENTIFIER
    ::= { cevChassis 1340 }

-- Nexus 6001 switch with 48x10G-BaseT + 4xQSFP ports

cevChassisWsC2960P48PstL  OBJECT IDENTIFIER
    ::= { cevChassis 1342 }

-- 48-port PoE, 2+2 1G uplinks, LAN Base

cevChassisWsC2960P24PcL  OBJECT IDENTIFIER
    ::= { cevChassis 1343 }

-- 24-port PoE, 2/2 1G uplinks, LAN Base

cevChassisWsC2960P24LcL  OBJECT IDENTIFIER
    ::= { cevChassis 1344 }

-- 24-port, partial PoE 2/2 1G uplinks, LAN Base

cevChassisWsC2960P48TcL  OBJECT IDENTIFIER
    ::= { cevChassis 1345 }

-- 48-port, 2/2 1G uplinks, LAN Base

cevChassisWsC2960P24TcL  OBJECT IDENTIFIER
    ::= { cevChassis 1346 }

-- 24-port, 2/2 1G uplinks, LAN Base

cevChassisWsC2960P48PstS  OBJECT IDENTIFIER
    ::= { cevChassis 1347 }

-- 48-port PoE, 2+2 1G uplinks, LAN Lite

cevChassisWsC2960P24PcS  OBJECT IDENTIFIER
    ::= { cevChassis 1348 }

-- 24-port PoE, 2/2 1G uplinks, LAN Lite

cevChassisWsC2960P24LcS  OBJECT IDENTIFIER
    ::= { cevChassis 1349 }

-- 24-port, partial PoE 2/2 1G uplinks, LAN Lite

cevChassisWsC2960P48TcS  OBJECT IDENTIFIER
    ::= { cevChassis 1350 }

-- 48-port, 2/2 1G uplinks, LAN Lite

cevChassisWsC2960P24TcS  OBJECT IDENTIFIER
    ::= { cevChassis 1351 }

-- 24-port, 2/2 1G uplinks, LAN Lite

cevChassisN77c7718  OBJECT IDENTIFIER
    ::= { cevChassis 1352 }

-- Nexus7700 18-slot chassis

cevChassisN77c7710  OBJECT IDENTIFIER
    ::= { cevChassis 1353 }

-- Nexus7700 10-slot chassis

cevChassisASR901AC10G  OBJECT IDENTIFIER
    ::= { cevChassis 1380 }

-- ASR901 10G AC platform with TDM & Eth interfaces

cevChassisASR901DC10G  OBJECT IDENTIFIER
    ::= { cevChassis 1381 }

-- ASR901 10G DC platform with TDM & Eth interfaces

cevChassisASR901eAC10G  OBJECT IDENTIFIER
    ::= { cevChassis 1382 }

-- ASR901 10G AC platform with Eth interfaces

cevChassisASR901eDC10G  OBJECT IDENTIFIER
    ::= { cevChassis 1383 }

-- ASR901 10G DC platform with Eth interfaces

cevChassisN3KC3172PQ10GE  OBJECT IDENTIFIER
    ::= { cevChassis 1388 }

-- Cisco chassis for N3K / QuickIron2

cevChassisN3KC3172TQ10GT  OBJECT IDENTIFIER
    ::= { cevChassis 1389 }

-- Cisco chassis for N3K / QuickZinc2

cevChassisN3KC3132Q40GE  OBJECT IDENTIFIER
    ::= { cevChassis 1390 }

-- Cisco chassis for N3K / Neptune-GE

cevChassisN3KC3132Q40GS  OBJECT IDENTIFIER
    ::= { cevChassis 1391 }

-- Cisco chassis for N3K / Neptune-GS

cevChassisASR9001S  OBJECT IDENTIFIER
    ::= { cevChassis 1392 }

-- ASR-9001 Chassis lowspeed

cevChassisIE20008T67B  OBJECT IDENTIFIER
    ::= { cevChassis 1393 }

-- Cisco IE2000 IP67 Variant Switch with  8 port 10/100 downlink, LAN Base Image

cevChassisIE200016T67B  OBJECT IDENTIFIER
    ::= { cevChassis 1394 }

-- Cisco IE2000 IP67 Variant Switch with 16 port 10/100 downlink, LAN Base Image

cevChassisIE200024T67B  OBJECT IDENTIFIER
    ::= { cevChassis 1395 }

-- Cisco IE2000 IP67 Variant Switch with 24 port 10/100 downlink, LAN Base Image

cevChassisIE20008T67PGE  OBJECT IDENTIFIER
    ::= { cevChassis 1396 }

-- Cisco IE2000 IP67 Variant Switch with  4 port 10/100 downlink, 4-port POE /POE+, 2 10/100/1000 uplink, LAN Base Image, can support PTP, NAT

cevChassisIE200016T67PGE  OBJECT IDENTIFIER
    ::= { cevChassis 1397 }

-- Cisco IE2000 IP67 Variant Switch with  8 port 10/100 downlink, 8-port POE / 4-port POE+, 2 10/100/1000 uplink, LAN Base Image, can support PTP, NAT

cevChassisRAIE1783ZMS8TA  OBJECT IDENTIFIER
    ::= { cevChassis 1398 }

-- Rockwell IE2000 IP67 Variant Switch with  8 port 10/100 downlink, LAN Base Image

cevChassisRAIE1783ZMS16TA  OBJECT IDENTIFIER
    ::= { cevChassis 1399 }

-- Rockwell IE2000 IP67 Variant Switch with  16 port 10/100 downlink, LAN Base Image

cevChassisRAIE1783ZMS24TA  OBJECT IDENTIFIER
    ::= { cevChassis 1400 }

-- Rockwell IE2000 IP67 Variant Switch with  24 port 10/100 downlink,  LAN Base Image

cevChassisRAIE1783ZMS4T4E2TGP  OBJECT IDENTIFIER
    ::= { cevChassis 1401 }

-- Rockwell IE2000 IP67 Variant Switch with 4 port 10/100 downlink, 4-port POE /POE+, 2 10/100/1000 uplink, LAN Base Image, can support PTP, NAT

cevChassisRAIE1783ZMS8T8E2TGP  OBJECT IDENTIFIER
    ::= { cevChassis 1402 }

-- Rockwell IE2000 IP67 Variant Switch with  8 port 10/100 downlink, 8-port POE / 4-port POE+, 2 10/100/1000 uplink , LAN Base Image, can support PTP, NAT

cevChassisCDScde2502s5  OBJECT IDENTIFIER
    ::= { cevChassis 1408 }

-- Cisco Content Delivery System Model CDE-250-2S5

cevChassisN6KC600172UP  OBJECT IDENTIFIER
    ::= { cevChassis 1410 }

-- Nexus 6000 Series 1RU switch with 48 ports fixed 10G(SFP+) Unified Ports,  6 ports fixed 40G (QSFP+)

cevChassisN3KC3132Q40G  OBJECT IDENTIFIER
    ::= { cevChassis 1417 }

-- Neptune-CR chassis Request

cevChassisDSC9706  OBJECT IDENTIFIER
    ::= { cevChassis 1420 }

-- DS-C9706, Chassis for MDS-9706 6-slot Director Switch

cevChassisC6800IA48FPD  OBJECT IDENTIFIER
    ::= { cevChassis 1424 }

-- Catalyst 6800IA 48 Gig Downlinks and 2 SFP+ uplink with support for a 2 x 10G stacking module. POE support for 740W

cevChassisC6800IA48TD  OBJECT IDENTIFIER
    ::= { cevChassis 1425 }

-- Catalyst 6800IA 48 Gig Downlinks and 2 SFP+ uplink with support for a 2 x 10G stacking module

cevChassisN9Kc9508  OBJECT IDENTIFIER
    ::= { cevChassis 1467 }

-- Nexus 9500 series chassis N9K-C9508

cevChassisME12006sAO  OBJECT IDENTIFIER
    ::= { cevChassis 1469 }

-- Cisco ME 1200 Outdoor Carrier Ethernet Access Demarcation Device, with 4 GE SFP ports and 2 RJ45 ports, AC power supply

cevChassisME12006sD  OBJECT IDENTIFIER
    ::= { cevChassis 1470 }

-- Cisco ME 1200 Indoor Carrier Ethernet Access Demarcation Device, with 4 GE SFP ports and 2 RJ45 ports, DC power supply

cevChassisME12006sA  OBJECT IDENTIFIER
    ::= { cevChassis 1471 }

-- Cisco ME 1200 Indoor Carrier Ethernet Access Demarcation Device, with 4 GE SFP ports and 2 RJ45 ports, AC power supply

cevChassis1783SR  OBJECT IDENTIFIER
    ::= { cevChassis 1472 }

-- Stratix S5900 K9 Hardened Router for Rockwell Automation with 1 Gigabit Ethernet WAN, 4 Fast Ethernet LAN

cevChassisN6kC6004  OBJECT IDENTIFIER
    ::= { cevChassis 1489 }

-- Nexus 6004 Switch with 6 Power Supplies, 4 Fan Modules and 96Q 40GE Ethernet/FCoE ports

cevChassisDSC9148SK9  OBJECT IDENTIFIER
    ::= { cevChassis 1491 }

-- Chassis for 16G MDS 9148 fabric swtich

cevChassisRT1081K9  OBJECT IDENTIFIER
    ::= { cevChassis 1494 }

-- Router 1081 Fast Ethernet Router

cevChassisRT1091FK9  OBJECT IDENTIFIER
    ::= { cevChassis 1495 }

-- Router 1091 GigaE SecRouter

cevChassisRT2241K9  OBJECT IDENTIFIER
    ::= { cevChassis 1496 }

-- Router 2241 w/2 GE,2 EHWIC slots,256MB CF,512MB DRAM,IP Base

cevChassisRT2221K9  OBJECT IDENTIFIER
    ::= { cevChassis 1497 }

-- Router 2221 Modular Router, 2 GE, 2 EHWIC slots, 512DRAM, IP Base

cevChassisRT2241WCK9  OBJECT IDENTIFIER
    ::= { cevChassis 1498 }

-- Router 2241 Router w/802.11 a/b/g/n China Compliant WLAN ISM

cevChassisRT3211K9  OBJECT IDENTIFIER
    ::= { cevChassis 1499 }

-- Router 3211 w/3 GE,4 EHWIC,2 DSP,1 SM,256MB CF,512MB DRAM,IPB

cevChassisRT3221K9  OBJECT IDENTIFIER
    ::= { cevChassis 1500 }

-- Router 3221 w/3 GE,4 EHWIC,3 DSP,1 SM,256MB CF,512MB DRAM,IPB

cevChassisRT3201K9  OBJECT IDENTIFIER
    ::= { cevChassis 1501 }

-- Router 3201 w/2 GE,4 EHWIC,2 DSP,256MB CF,512MB DRAM,IP Base

cevChassisN9KC93128TX  OBJECT IDENTIFIER
    ::= { cevChassis 1510 }

-- Cisco chassis for 3RU TOR, 96x10GT+8x40G QSFP

cevBackplane  OBJECT IDENTIFIER
    ::= { cevMIBObjects 4 }

cevBackplaneAtm  OBJECT IDENTIFIER
    ::= { cevBackplane 4 }

-- LS1010 Chassis

cevBackplaneCat5500  OBJECT IDENTIFIER
    ::= { cevBackplane 5 }

-- Catalyst 5500 Chassis

cevBackplaneCat6400  OBJECT IDENTIFIER
    ::= { cevBackplane 6 }

-- Catalyst 6400 Chassis

cevBackplaneCat8510  OBJECT IDENTIFIER
    ::= { cevBackplane 7 }

-- Catalyst 8510 Layer 3 Router/Switch

cevBackplaneCat8540  OBJECT IDENTIFIER
    ::= { cevBackplane 8 }

-- Catalyst 8540 Layer 3 Router/Switch

cevBackplaneMGX8850  OBJECT IDENTIFIER
    ::= { cevBackplane 9 }

-- MGX8850 Chassis

cevBackplaneMGX8820  OBJECT IDENTIFIER
    ::= { cevBackplane 10 }

-- MGX8820 Chassis

cevBackplaneBPXSes  OBJECT IDENTIFIER
    ::= { cevBackplane 11 }

-- BPXSes Chassis

cevBackplaneIGXSes  OBJECT IDENTIFIER
    ::= { cevBackplane 12 }

-- IGXSes Chassis

cevBackplaneCat6000  OBJECT IDENTIFIER
    ::= { cevBackplane 13 }

-- Catalyst 6000 Backplane

cevBackplaneCat6500  OBJECT IDENTIFIER
    ::= { cevBackplane 14 }

-- Catalyst 6500 Backplane

cevBackplaneMGX8950  OBJECT IDENTIFIER
    ::= { cevBackplane 15 }

-- Backplane for MGX8950 switch

cevBackplaneONS15540Fixed  OBJECT IDENTIFIER
    ::= { cevBackplane 16 }

-- Cisco ONS 15540 ESP electrical backplane with fixed optical backplane

cevBackplaneCat4006  OBJECT IDENTIFIER
    ::= { cevBackplane 18 }

-- Catalyst 4006 Backplane

cevBackplaneMGX8830  OBJECT IDENTIFIER
    ::= { cevBackplane 19 }

-- MGX8830 Chassis

cevBackplaneONS15530  OBJECT IDENTIFIER
    ::= { cevBackplane 20 }

-- Cisco ONS 15530 electrical backplane

cevBackplaneCat4507  OBJECT IDENTIFIER
    ::= { cevBackplane 23 }

-- Catalyst 4507 Backplane

cevBackplaneCat4503  OBJECT IDENTIFIER
    ::= { cevBackplane 24 }

-- Catalyst 4503 Backplane

cevBackplaneCat4506  OBJECT IDENTIFIER
    ::= { cevBackplane 25 }

-- Catalyst 4506 Backplane

cevBackplaneDSC9506  OBJECT IDENTIFIER
    ::= { cevBackplane 26 }

-- MDS 9506 Backplane

cevBackplaneDSC9509  OBJECT IDENTIFIER
    ::= { cevBackplane 27 }

-- MDS 9509 Backplane

cevBackplaneDSC9513  OBJECT IDENTIFIER
    ::= { cevBackplane 28 }

-- MDS 9513 Backplane

cevBackplaneONS15540ESPx  OBJECT IDENTIFIER
    ::= { cevBackplane 29 }

-- Cisco ONS 15540 ESPx backplane

cevBackplaneUnknown  OBJECT IDENTIFIER
    ::= { cevBackplane 30 }

-- Unknown Backplane

cevBackplaneCat4510  OBJECT IDENTIFIER
    ::= { cevBackplane 31 }

-- Catalyst 4510R Backplane

cevBackplaneDSC9140K9  OBJECT IDENTIFIER
    ::= { cevBackplane 32 }

-- DS-C9140-K9 - MDS 9140 Backplane

cevBackplaneBMGX8850  OBJECT IDENTIFIER
    ::= { cevBackplane 33 }

-- Model B Backplane for MGX8850

cevBackplaneBMGX8950  OBJECT IDENTIFIER
    ::= { cevBackplane 34 }

-- Model B Backplane for MGX8950

cevBackplaneCisco7600  OBJECT IDENTIFIER
    ::= { cevBackplane 35 }

-- Cisco 7600 Backplane

cevBackplaneBMGX8830  OBJECT IDENTIFIER
    ::= { cevBackplane 36 }

-- Model B Backplane for MGX8830 switch

cevBackplaneDSC9216AK9  OBJECT IDENTIFIER
    ::= { cevBackplane 37 }

-- DS-C9216A-K9 - MDS 9216 Backplane

cevBackplaneMGX8880  OBJECT IDENTIFIER
    ::= { cevBackplane 38 }

-- Backplane for Cisco MGX8880 chassis

cevBackplane6SlotsRCON8850  OBJECT IDENTIFIER
    ::= { cevBackplane 39 }

-- A 6-slot RCON for MGX8850/8880 chassis. Redundancy CONnector (RCON) is intended to provide 1:N front card redundancy solution for MGX8xxx solution where N can be 1,2,3,4,5.

cevBackplane4SlotsRCON8850  OBJECT IDENTIFIER
    ::= { cevBackplane 40 }

-- A 4-slot RCON for MGX8850/8880 chassis. Redundancy CONnector (RCON) is intended to provide 1:N front card redundancy solution for MGX8xxx solution where N can be 1,2,3,4,5.

cevBackplane4SlotsRCON8830  OBJECT IDENTIFIER
    ::= { cevBackplane 41 }

-- A 4-slot RCON for MGX8830 chassis. Redundancy CONnector (RCON) is intended to provide 1:N front card redundancy solution for MGX8xxx solution where N can be 1,2,3,4,5.

cevBackplaneDSX9116K9  OBJECT IDENTIFIER
    ::= { cevBackplane 42 }

-- mds-9116 backplane type

cevBackplaneONS15310  OBJECT IDENTIFIER
    ::= { cevBackplane 43 }

-- Cisco ONS 15310 Backplane

cevBackplaneCat4503e  OBJECT IDENTIFIER
    ::= { cevBackplane 48 }

-- Catalyst 4503-E Backplane

cevBackplaneCat4506e  OBJECT IDENTIFIER
    ::= { cevBackplane 49 }

-- Catalyst 4506-E Backplane

cevBackplaneCat4507re  OBJECT IDENTIFIER
    ::= { cevBackplane 50 }

-- Catalyst 4507R-E Backplane

cevBackplaneCat4510re  OBJECT IDENTIFIER
    ::= { cevBackplane 51 }

-- Catalyst 4510R-E Backplane

cevBackplaneN7Kc7010  OBJECT IDENTIFIER
    ::= { cevBackplane 52 }

-- Nexus7000 10 slot N7K backplane

cevBackplaneCatRfgw  OBJECT IDENTIFIER
    ::= { cevBackplane 53 }

-- RF gateway backplane

cevBackplaneN7Kc7018  OBJECT IDENTIFIER
    ::= { cevBackplane 55 }

-- backplane for Nexus7000 18 slot N7K

cevBackplaneMXE5600  OBJECT IDENTIFIER
    ::= { cevBackplane 56 }

-- Backplane for Cisco MXE 5600 platform

cevBackplaneN7Kc7009  OBJECT IDENTIFIER
    ::= { cevBackplane 57 }

-- MosPort9 N7K-C7009 Nexus-9-slot-backplane

cevBackplaneN7Kc7004  OBJECT IDENTIFIER
    ::= { cevBackplane 61 }

-- Nexus7000 4slot zonda n7k backplane N7K-C7004

cevBackplaneDSC9710  OBJECT IDENTIFIER
    ::= { cevBackplane 63 }

-- DS-C9710, backplane for MDS 10-Slot Director Switch

cevBackplaneN77c7718  OBJECT IDENTIFIER
    ::= { cevBackplane 64 }

-- Nexus7700 18-slot backplane

cevBackplaneN77c7710  OBJECT IDENTIFIER
    ::= { cevBackplane 65 }

-- Nexus7700 10-slot backplane

cevBackplaneDSC9706  OBJECT IDENTIFIER
    ::= { cevBackplane 68 }

-- Backplane for MDS-9706 6-slot Director Switch
--   

-- Acronyms used in the cevContainer section:
-- EARLDB   EARL DaughterBoard
-- PBD   Packet-Buffer DaughterBoard

cevContainer  OBJECT IDENTIFIER
    ::= { cevMIBObjects 5 }

cevContainerSlot  OBJECT IDENTIFIER
    ::= { cevContainer 1 }

-- represents slots on the chassis

cevContainerDaughterCard  OBJECT IDENTIFIER
    ::= { cevContainer 2 }

-- represents slots for a daughter card

cevContainerPCMCIA  OBJECT IDENTIFIER
    ::= { cevContainer 12 }

cevContainerDSPModuleSlot  OBJECT IDENTIFIER
    ::= { cevContainer 16 }

cevContainerCat8500Carrier  OBJECT IDENTIFIER
    ::= { cevContainer 17 }

-- Module Carrier that can carry 2 submodules per slot

cevContainerCat8500CpuSwitchAndFeature  OBJECT IDENTIFIER
    ::= { cevContainer 18 }

-- Switch Processor with feature card FC1

cevContainerCat8500CpuSwitchAndFeaturePFQ  OBJECT IDENTIFIER
    ::= { cevContainer 19 }

-- Switch Processor with feature card FC-PFQ

cevContainerCat8500SuperCarrier  OBJECT IDENTIFIER
    ::= { cevContainer 20 }

-- Super Module Carrier that can carry 2 submodules per slot

cevContainerCat8500CpuRoute  OBJECT IDENTIFIER
    ::= { cevContainer 21 }

-- Routing Processor

cevContainerCat8500Switch10GAndFC  OBJECT IDENTIFIER
    ::= { cevContainer 22 }

-- 10 Gigabit Switch Fabric with Feature Card option

cevContainerCat8500Switch10GNoFC  OBJECT IDENTIFIER
    ::= { cevContainer 23 }

-- 10 Gigabit Switch Fabric without Feature Card option

cevContainerDslamSlot  OBJECT IDENTIFIER
    ::= { cevContainer 24 }

-- Cisco 6100, 6130, 6260 DSLAM Chassis General Purpose Slot

cevContainerC6260PsSlot  OBJECT IDENTIFIER
    ::= { cevContainer 25 }

-- Cisco 6260 Power Supply Slot

cevContainerC6260FanSlot  OBJECT IDENTIFIER
    ::= { cevContainer 26 }

-- Cisco 6260 Fan Tray Slot

cevContainerDslamControllerSlot  OBJECT IDENTIFIER
    ::= { cevContainer 27 }

-- Cisco 6100, 6130, 6260 DSLAM Chassis System Controller Slot

cevContainerDslamNi2DcSlot  OBJECT IDENTIFIER
    ::= { cevContainer 28 }

-- Cisco 6100, 6130, 6260 DSLAM Chassis NI-2 Daughter Card Slot

cevContainerPsmSlot  OBJECT IDENTIFIER
    ::= { cevContainer 31 }

-- Processor Switch Module slot for MGX8800 series

cevContainerSmSlot  OBJECT IDENTIFIER
    ::= { cevContainer 32 }

-- Service Module slot for MGX8800 series

cevContainerMGX8800FanTray  OBJECT IDENTIFIER
    ::= { cevContainer 33 }

-- Fan Tray container for MGX8800 series products, containing 9 fans; only 8 fans need to be working

cevContainerSrmSlot  OBJECT IDENTIFIER
    ::= { cevContainer 34 }

-- Slot in MGX8800 series chassis that holds the Service Redundancy Module

cevContainerMGX8800ACPSTray  OBJECT IDENTIFIER
    ::= { cevContainer 35 }

-- AC Power Supply Tray for MGX8800 Universal Chassis

cevContainerSESFanTray  OBJECT IDENTIFIER
    ::= { cevContainer 36 }

-- Fan Tray Container for SES (Service Expansion Shelf) products, containing 8 fans

cevContainer12012TopBlowerBay  OBJECT IDENTIFIER
    ::= { cevContainer 37 }

-- Top fan blower bay for Cisco 12012

cevContainer12012BottomBlowerBay  OBJECT IDENTIFIER
    ::= { cevContainer 38 }

-- Bottom fan blower bay for Cisco 12012

cevContainer12012ModuleBay  OBJECT IDENTIFIER
    ::= { cevContainer 39 }

-- Module bay for Cisco 12012

cevContainer12012SwitchFabricBay  OBJECT IDENTIFIER
    ::= { cevContainer 40 }

-- Switch Fabric bay for Cisco 12012

cevContainer12012PowerSupplyBay  OBJECT IDENTIFIER
    ::= { cevContainer 41 }

-- Power Supply  bay for Cisco 12012

cevContainer12008PowerBlowerBay  OBJECT IDENTIFIER
    ::= { cevContainer 42 }

-- Power supply fan blower bay for Cisco 12008

cevContainer12008MainBlowerBay  OBJECT IDENTIFIER
    ::= { cevContainer 43 }

-- Main blower bay for Cisco 12008

cevContainer12008ModuleBay  OBJECT IDENTIFIER
    ::= { cevContainer 44 }

-- Module bay for Cisco 12008

cevContainer12008SwitchFabricBay  OBJECT IDENTIFIER
    ::= { cevContainer 45 }

-- Switch Fabric bay for Cisco 12008

cevContainer12008PowerSupplyBay  OBJECT IDENTIFIER
    ::= { cevContainer 46 }

-- Power supply bay for Cisco 12008

cevContainerC6160PsSlot  OBJECT IDENTIFIER
    ::= { cevContainer 48 }

-- Power Supply slot for Cisco 6160

cevContainerC6160FanSlot  OBJECT IDENTIFIER
    ::= { cevContainer 49 }

-- Blower Module slot for Cisco 6160

cevContainerMGXXm60Slot  OBJECT IDENTIFIER
    ::= { cevContainer 52 }

-- Slot in selected MGX Series chassis which can hold XM60 Cross Bar Switch Module

cevContainerCat8500CMPMCarrier  OBJECT IDENTIFIER
    ::= { cevContainer 55 }

-- CMPM Module Carrier that can carry 2 XPIF PM cards per slot

cevContainer12010TopBlowerBay  OBJECT IDENTIFIER
    ::= { cevContainer 56 }

-- Top fan blower bay for gsr 12010

cevContainer12010BottomBlowerBay  OBJECT IDENTIFIER
    ::= { cevContainer 57 }

-- Bottom fan blower bay for gsr 12010

cevContainer12010UpperModuleBay  OBJECT IDENTIFIER
    ::= { cevContainer 58 }

-- Upper Module bay for gsr

cevContainer12010LowerModuleBay  OBJECT IDENTIFIER
    ::= { cevContainer 59 }

-- Lower Module bay for gsr

cevContainer12010SwitchFabricBay  OBJECT IDENTIFIER
    ::= { cevContainer 60 }

-- Switch Fabric bay for gsr 12010

cevContainer12010PowerSupplyBay  OBJECT IDENTIFIER
    ::= { cevContainer 61 }

-- Power Supply  bay for gsr 12010

cevContainer12010PowerBlowerBay  OBJECT IDENTIFIER
    ::= { cevContainer 62 }

-- Power Blower  bay for gsr 12010

cevContainer12010MainBlowerBay  OBJECT IDENTIFIER
    ::= { cevContainer 63 }

-- Main blower bay for gsr 12010

cevContainer12406ModuleBay  OBJECT IDENTIFIER
    ::= { cevContainer 64 }

-- Line Card/Routing Processor Bay for gsr 12406

cevContainer12406FabricAlarmBay  OBJECT IDENTIFIER
    ::= { cevContainer 65 }

-- Fabric and Alarm card bay for gsr 12406

cevContainer12406PowerSupplyBay  OBJECT IDENTIFIER
    ::= { cevContainer 66 }

-- Power Supply bay for gsr 12406

cevContainer12406MainBlowerBay  OBJECT IDENTIFIER
    ::= { cevContainer 67 }

-- Main blower bay for gsr 12406

cevContainer12410TopBlowerBay  OBJECT IDENTIFIER
    ::= { cevContainer 68 }

-- Top Fan blower bay for gsr 12410

cevContainer12410BottomBlowerBay  OBJECT IDENTIFIER
    ::= { cevContainer 69 }

-- Bottom Fan blower bay for gsr 12410

cevContainer12410UpperModuleBay  OBJECT IDENTIFIER
    ::= { cevContainer 70 }

-- Upper Module Bay for gsr 12410

cevContainer12410LowerModuleBay  OBJECT IDENTIFIER
    ::= { cevContainer 71 }

-- Lower Module Bay for gsr 12410

cevContainer12410SwitchFabricBay  OBJECT IDENTIFIER
    ::= { cevContainer 72 }

-- Switch Fabric bay for gsr 12410

cevContainer12410PowerSupplyBay  OBJECT IDENTIFIER
    ::= { cevContainer 73 }

-- Power Supply  bay for gsr 12410

cevContainer12410PowerBlowerBay  OBJECT IDENTIFIER
    ::= { cevContainer 74 }

-- Power Blower  bay for gsr 12410

cevContainer12410MainBlowerBay  OBJECT IDENTIFIER
    ::= { cevContainer 75 }

-- Main blower bay for gsr 12410

cevContainerONS15540CardSlot  OBJECT IDENTIFIER
    ::= { cevContainer 76 }

-- Cisco ONS 15540 ESP processor, mux/demux or transponder module slot

cevContainerONS15540FanTraySlot  OBJECT IDENTIFIER
    ::= { cevContainer 77 }

-- Cisco ONS 15540 ESP Fan Tray Slot

cevContainerONS15540TspSubslot  OBJECT IDENTIFIER
    ::= { cevContainer 78 }

-- Container for ONS 15540 ESP Transponder card

cevContainerONS15540MDXSubslot  OBJECT IDENTIFIER
    ::= { cevContainer 79 }

-- Container for ONS 15540 ESP Mux/Demux subcard

cevContainerONS15540SubCardSlot  OBJECT IDENTIFIER
    ::= { cevContainer 80 }

-- Container for ONS 15540 ESP or Mux/Demux subcard

cevContainer12404ModuleBay  OBJECT IDENTIFIER
    ::= { cevContainer 81 }

-- LineCard/Routing Processor Bay for GSR 12404

cevContainer12404FabricAlarmBay  OBJECT IDENTIFIER
    ::= { cevContainer 82 }

-- Fabric and Alarm card Bay for GSR 12404

cevContainer12404PowerSupplyBay  OBJECT IDENTIFIER
    ::= { cevContainer 83 }

-- Power Supply bay for GSR 12404

cevContainer12404MainBlowerBay  OBJECT IDENTIFIER
    ::= { cevContainer 84 }

-- Main blower bay for GSR 12404

cevContainerC7304PowerSupplyBay  OBJECT IDENTIFIER
    ::= { cevContainer 85 }

-- Cisco 7300 platform Power Supply Slot

cevContainerC10KSlot  OBJECT IDENTIFIER
    ::= { cevContainer 86 }

-- Cisco 10000 General Purpose Slot

cevContainerC10KPowerSupplySlot  OBJECT IDENTIFIER
    ::= { cevContainer 87 }

-- Cisco 10000 Power Supply Slot

cevContainerC10KFanTraySlot  OBJECT IDENTIFIER
    ::= { cevContainer 88 }

-- Cisco 10000 Fan Tray Bay

cevContainerC10KFlashCardSlot  OBJECT IDENTIFIER
    ::= { cevContainer 89 }

-- Cisco 10000 Flash Card Slot

cevContainerCat4kFanTrayBay  OBJECT IDENTIFIER
    ::= { cevContainer 90 }

-- Cisco Catalyst 4000 fan tray bay

cevContainerCat4kPowerSupplyBay  OBJECT IDENTIFIER
    ::= { cevContainer 91 }

-- Power supply bay for Cisco Catalyst 4000

cevContainerCat4kPEMBay  OBJECT IDENTIFIER
    ::= { cevContainer 92 }

-- Power Entry Module Bay for Cisco Catalyst 4000

cevContainer12016PowerBlowerBay  OBJECT IDENTIFIER
    ::= { cevContainer 93 }

-- Power Blower  bay for gsr 12016

cevContainer12016LowerModuleBay  OBJECT IDENTIFIER
    ::= { cevContainer 94 }

-- Lower Module bay for gsr 12016

cevContainer12016SwitchFabricBay  OBJECT IDENTIFIER
    ::= { cevContainer 95 }

-- Switch Fabric bay for gsr 12016

cevContainer12016PowerSupplyBay  OBJECT IDENTIFIER
    ::= { cevContainer 96 }

-- Power Supply  bay for gsr 12016

cevContainer12016TopBlowerBay  OBJECT IDENTIFIER
    ::= { cevContainer 97 }

-- Top fan blower bay for gsr 12016

cevContainer12016BottomBlowerBay  OBJECT IDENTIFIER
    ::= { cevContainer 98 }

-- Bottom fan blower bay for gsr 12016

cevContainer12016UpperModuleBay  OBJECT IDENTIFIER
    ::= { cevContainer 99 }

-- Upper Module bay for gsr 12016

cevContainerONS15530CardSlot  OBJECT IDENTIFIER
    ::= { cevContainer 100 }

-- Cisco ONS 15530 processor or transponder or any line card module slot

cevContainerONS15530FanTraySlot  OBJECT IDENTIFIER
    ::= { cevContainer 102 }

-- Cisco ONS 15530 Fan Tray Slot

cevContainerONS15530PSSlot  OBJECT IDENTIFIER
    ::= { cevContainer 103 }

-- Cisco ONS 15530 Power Supply Slot

cevContainerONS15530SubCardSlot  OBJECT IDENTIFIER
    ::= { cevContainer 104 }

-- Cisco ONS 15530 SubSlot for Mux/Demux, OSC module

cevContainerONS15530PortSlot  OBJECT IDENTIFIER
    ::= { cevContainer 105 }

-- Cisco ONS 15530 slot for transceiver

cevContainerONS15540PortSlot  OBJECT IDENTIFIER
    ::= { cevContainer 106 }

-- Container for pluggable transceivers

cevContainerCat4kContainerPSBay  OBJECT IDENTIFIER
    ::= { cevContainer 111 }

-- Container of Power Supply Bays for Cisco Catalyst 4000
-- removed oids 112 and 113.

cevContainerSPABay  OBJECT IDENTIFIER
    ::= { cevContainer 114 }

-- Represents sub-slots in the carrier cards where Shared Port Adaptor (SPA) cards are inserted.

cevContainerSFP  OBJECT IDENTIFIER
    ::= { cevContainer 115 }

-- Represents a place-holder on the card where an  SFP module is inserted.

cevContainerGsrAlarmSlot  OBJECT IDENTIFIER
    ::= { cevContainer 116 }

-- Represents alarm card slot on GSR

cevContainerGsrPowerSupplySlot  OBJECT IDENTIFIER
    ::= { cevContainer 117 }

-- Represents power supply slot on GSR

cevContainerGsrFanBlowerSlot  OBJECT IDENTIFIER
    ::= { cevContainer 118 }

-- Represents fan blower slot on GSR

cevContainerGsrSwitchFabricSlot  OBJECT IDENTIFIER
    ::= { cevContainer 119 }

-- Represents switch fabric slot on GSR

cevContainerONS15252CardSlot  OBJECT IDENTIFIER
    ::= { cevContainer 120 }

-- Cisco ONS 15252 processor module or client line interface port module slot

cevContainerONS15201CardSlot  OBJECT IDENTIFIER
    ::= { cevContainer 121 }

-- Cisco ONS 15201  client line interface port module slot

cevContainerSupFabricSlot  OBJECT IDENTIFIER
    ::= { cevContainer 122 }

-- Container for supervisor/fabric slot

cevContainerLineCardSlot  OBJECT IDENTIFIER
    ::= { cevContainer 123 }

-- Container for supervisor/fabric slot

cevContainer9506PowerSupplyBay  OBJECT IDENTIFIER
    ::= { cevContainer 124 }

-- Container for 9506 Power supply bay

cevContainer9509PowerSupplyBay  OBJECT IDENTIFIER
    ::= { cevContainer 125 }

-- Container for 9509 Power supply bay

cevContainer9513PowerSupplyBay  OBJECT IDENTIFIER
    ::= { cevContainer 126 }

-- Container for 9513 Power supply bay

cevContainer9506FanBay  OBJECT IDENTIFIER
    ::= { cevContainer 127 }

-- Container for 9506 Fan bay

cevContainer9509FanBay  OBJECT IDENTIFIER
    ::= { cevContainer 128 }

-- Container for 9509 Fan bay

cevContainer9513FanBay  OBJECT IDENTIFIER
    ::= { cevContainer 129 }

-- Container for 9513 Fan bay

cevContainer9216FanBay  OBJECT IDENTIFIER
    ::= { cevContainer 130 }

-- Container for 9216 Fan bay

cevContainer9216PowerSupplyBay  OBJECT IDENTIFIER
    ::= { cevContainer 131 }

-- Container for 9216 Power supply bay

cevContainerC7300CCPA  OBJECT IDENTIFIER
    ::= { cevContainer 132 }

-- 7300 Port Adapter Carrier Card

cevContainerPABay  OBJECT IDENTIFIER
    ::= { cevContainer 133 }

-- Represents sub-slots in the jacket type line cards where port adapters are inserted

cevChassisCr4430  OBJECT IDENTIFIER
    ::= { cevContainer 134 }

-- Cisco Content Router Model 4430

cevMgx2uPlenumFanTray  OBJECT IDENTIFIER
    ::= { cevContainer 135 }

-- 2RU Exhaust Plenum with Integrated Fan Tray in MGX8850 and MGX8950

cevContainerMDSPowerSupplyBay  OBJECT IDENTIFIER
    ::= { cevContainer 136 }

-- Container for MDS PowerSupply Bay

cevContainerMDSFanTrayBay  OBJECT IDENTIFIER
    ::= { cevContainer 137 }

-- Container for MDS Fan tray Bay

cevContainerFlashCardSlot  OBJECT IDENTIFIER
    ::= { cevContainer 138 }

-- Generic flash card slot

cevContainerFanTraySlot  OBJECT IDENTIFIER
    ::= { cevContainer 139 }

-- Generic fan tray slot

cevContainerPowerSupplyBay  OBJECT IDENTIFIER
    ::= { cevContainer 140 }

-- Generic power supply bay

cevContainerPowerSupply  OBJECT IDENTIFIER
    ::= { cevContainer 141 }

-- Generic power supply subcontainer for bay

cevContainerGbic  OBJECT IDENTIFIER
    ::= { cevContainer 142 }

-- Generic gigabit port container

cevContainerCrs1RPSlot  OBJECT IDENTIFIER
    ::= { cevContainer 143 }

-- Cisco CRS1 route processor slot.

cevContainerCrs1LCDRPSlot  OBJECT IDENTIFIER
    ::= { cevContainer 144 }

-- Cisco CRS1 Line Card / Distributed Route Processor card slot

cevContainerCrs1FabricSlot  OBJECT IDENTIFIER
    ::= { cevContainer 145 }

-- Cisco CRS1 fabric card slot.

cevContainerCrs1AlarmSlot  OBJECT IDENTIFIER
    ::= { cevContainer 146 }

-- Cisco CRS1 alarm card slot.

cevContainerCrs1PowerSupplySlot  OBJECT IDENTIFIER
    ::= { cevContainer 147 }

-- Cisco CRS1 power supply slot.

cevContainerCrs1FanSlot  OBJECT IDENTIFIER
    ::= { cevContainer 148 }

-- Cisco CRS1 Fan controller slot.

cevContainerPowerSupplySlot  OBJECT IDENTIFIER
    ::= { cevContainer 149 }

-- Cisco Power Supply slot.

cevContainerVtt  OBJECT IDENTIFIER
    ::= { cevContainer 150 }

-- Generic VTT module container

cevContainerClock  OBJECT IDENTIFIER
    ::= { cevContainer 151 }

-- Generic clock module container

cevContainer10GigBasePort  OBJECT IDENTIFIER
    ::= { cevContainer 152 }

-- Generic 10 gigabit ethernet port container

cevContainerUmg9820ProcessorCard  OBJECT IDENTIFIER
    ::= { cevContainer 153 }

-- Container for umg9820 products processor card

cevContainerUmg9820PowerSupplyBay  OBJECT IDENTIFIER
    ::= { cevContainer 154 }

-- Container for umg9820 product's power supply

cevContainerUmg9820QamModuleSlot  OBJECT IDENTIFIER
    ::= { cevContainer 155 }

-- Container for umg9820 product's Qam card

cevContainerUmg9820FanTraySlot  OBJECT IDENTIFIER
    ::= { cevContainer 156 }

-- Container for umg9820 product's Fan Tray

cevContainer9116FanBay  OBJECT IDENTIFIER
    ::= { cevContainer 157 }

-- MDS 9116 Fan Bay Container

cevContainer9116PowerSupplyBay  OBJECT IDENTIFIER
    ::= { cevContainer 158 }

-- MDS 9116 Power Supply Container

cevContainerONS15310CardSlot  OBJECT IDENTIFIER
    ::= { cevContainer 159 }

-- Cisco ONS 15310 Line Card Slot

cevContainerGSR6Blwr  OBJECT IDENTIFIER
    ::= { cevContainer 160 }

-- Cisco 12000 6-slot Enhanced blower

cevContainerGSR10GSR16Blwr  OBJECT IDENTIFIER
    ::= { cevContainer 161 }

-- Cisco 12000 10-slot and 16-slot Enhanced blower

cevContainer9513RearFanBay  OBJECT IDENTIFIER
    ::= { cevContainer 162 }

-- Container for 9513 Rear Fan bay

cevContainerFabricSlot  OBJECT IDENTIFIER
    ::= { cevContainer 163 }

-- Container for Fabric cards

cevContainerCrs18RPSlot  OBJECT IDENTIFIER
    ::= { cevContainer 164 }

-- Cisco CRS-1 Series 8 Slots Route Processor Slot

cevContainerCrs18FabricSlot  OBJECT IDENTIFIER
    ::= { cevContainer 165 }

-- Cisco CRS-1 Series 8 Slots Fabric Card (Single) slot

cevContainerCrs1FabricShelfControllerSlot  OBJECT IDENTIFIER
    ::= { cevContainer 166 }

-- Cisco CRS-1 Series Fabric Card Chassis Shelf controller Slot

cevContainerCrs1FabricSwitchFabricSlot  OBJECT IDENTIFIER
    ::= { cevContainer 167 }

-- Cisco CRS-1 Series Fabric Card Chassis Switch Fabric Card (multi) Slot

cevContainerCrs1FabricFiberModuleSlot  OBJECT IDENTIFIER
    ::= { cevContainer 168 }

-- Cisco CRS-1 Series Fabric Card Chassis Fiber Module Slot

cevContainerCrs1FabricLEDModuleSlot  OBJECT IDENTIFIER
    ::= { cevContainer 169 }

-- Cisco CRS-1 Series Fabric Card Chassis LED Module Slot

cevPowerSupplyCrs1PowerSupplyShelf  OBJECT IDENTIFIER
    ::= { cevContainer 170 }

-- Cisco CRS-1 Series Chassis Power Supply Shelf

cevContainerTransceiver  OBJECT IDENTIFIER
    ::= { cevContainer 171 }

-- Represents a place-holder on the card where a transceiver module is inserted

cevContainer9124PowerSupplyBay  OBJECT IDENTIFIER
    ::= { cevContainer 173 }

-- Power Supply Bay for 24-port 1/2/4 Gig Supervisor Fabric Switch

cevContainer9124FanBay  OBJECT IDENTIFIER
    ::= { cevContainer 174 }

-- Fan Bay for 24-port 1/2/4 Gig Supervisor Fabric Storage Switch

cevContainerC3KPowerSupply  OBJECT IDENTIFIER
    ::= { cevContainer 175 }

-- Catalyst 3K Power supply slot

cevContainerC3KRemotePowerSupply  OBJECT IDENTIFIER
    ::= { cevContainer 176 }

-- Catalyst 3K Remote Power Supply (RPS) slot

cevContainerC3KBlower  OBJECT IDENTIFIER
    ::= { cevContainer 177 }

-- Catalyst 3K Blower / Fan slot

cevContainer9222iFanBay  OBJECT IDENTIFIER
    ::= { cevContainer 178 }

-- Fan bay in MDS 9222i Chassis

cevContainerN7Kc7010PowerSupplyBay  OBJECT IDENTIFIER
    ::= { cevContainer 179 }

-- container for Nexus7000 10 slot  N7K powersupply

cevContainerN7KC7010MainFanBay  OBJECT IDENTIFIER
    ::= { cevContainer 180 }

-- container for Nexus7000 10 slot N7K main system fan

cevContainerN7KC7010FabricFanBay  OBJECT IDENTIFIER
    ::= { cevContainer 181 }

-- container for Nexus7000 10 slot N7K fabric fan

cevContainerASR1000RPSlot  OBJECT IDENTIFIER
    ::= { cevContainer 182 }

-- ASR1000 Routing Processor Module Container

cevContainerASR1000FPSlot  OBJECT IDENTIFIER
    ::= { cevContainer 183 }

-- ASR1000 Forwarding Processor Module Container

cevContainerASR1000CCSlot  OBJECT IDENTIFIER
    ::= { cevContainer 184 }

-- ASR1000 Carrier Card Module Container

cevContainerASR1000PowerSupplyBay  OBJECT IDENTIFIER
    ::= { cevContainer 185 }

-- ASR1000 Power Supply / Fan Module container

cevContainerN5kC5020FanBay  OBJECT IDENTIFIER
    ::= { cevContainer 186 }

-- Container for N5kC5020 Fan bay

cevContainerN5kC5020PowerSupplyBay  OBJECT IDENTIFIER
    ::= { cevContainer 187 }

-- Container for N5kC5020 Power supply bay

cevContainerASR9KFanTraySlot  OBJECT IDENTIFIER
    ::= { cevContainer 188 }

-- ASR 90xx FanTray Container

cevContainerASR9KPowerSupplySlotDC  OBJECT IDENTIFIER
    ::= { cevContainer 189 }

-- ASR 90xx DC Power Entry Module Container

cevContainerASR9KPowerSupplySlotAC  OBJECT IDENTIFIER
    ::= { cevContainer 190 }

-- ASR 90xx AC Power Entry Module Container

cevContainerASR9KRSPSlot  OBJECT IDENTIFIER
    ::= { cevContainer 191 }

-- ASR 90xx Route/Switch Processor Module Container

cevContainerASR9KLCSlot  OBJECT IDENTIFIER
    ::= { cevContainer 192 }

-- ASR 90xx Line Card Module Container

cevContainerN7Kc7018PowerSupplyBay  OBJECT IDENTIFIER
    ::= { cevContainer 193 }

-- container for Nexus7000 18 slot N7K powersupply

cevContainerN7KC7018FanBay  OBJECT IDENTIFIER
    ::= { cevContainer 194 }

-- container for Nexus7000 18 slot N7K fan

cevContainerCrs1PowerShelfSlot  OBJECT IDENTIFIER
    ::= { cevContainer 195 }

-- Cisco CRS1 Power Shelf slot

cevContainerN5kC5010FanBay  OBJECT IDENTIFIER
    ::= { cevContainer 196 }

-- Container for N5kC5010 Fan bay

cevContainerN5kC5010PowerSupplyBay  OBJECT IDENTIFIER
    ::= { cevContainer 197 }

-- Container for N5kC5010 Power supply bay

cevContainerXFP  OBJECT IDENTIFIER
    ::= { cevContainer 198 }

-- XFP container

cevContainerAsr14kPowerSupplySlot  OBJECT IDENTIFIER
    ::= { cevContainer 199 }

-- Cisco ASR14000 Series Power Supply Slot

cevContainerAsr14kPowerShelfSlot  OBJECT IDENTIFIER
    ::= { cevContainer 200 }

-- Cisco ASR14000 Series Power Shelf Slot

cevContainerAsr14kFanTraySlot  OBJECT IDENTIFIER
    ::= { cevContainer 201 }

-- Cisco ASR14000 Series Fan Tray Slot

cevContainerAsr14kFabricCardSlot  OBJECT IDENTIFIER
    ::= { cevContainer 202 }

-- Cisco ASR14000 Series Fabric Card Slot

cevContainerAsr14kFPSlot  OBJECT IDENTIFIER
    ::= { cevContainer 203 }

-- Cisco ASR14000 Series Forwarding Processor Slot

cevContainerAsr14kRPSlot  OBJECT IDENTIFIER
    ::= { cevContainer 204 }

-- Cisco ASR14000 Series Route Processor Slot

cevContainerHardDiskSlot  OBJECT IDENTIFIER
    ::= { cevContainer 205 }

-- Generic Hard Disk slot to hold the Hard Disk

cevContainerNexusLogicalFabric  OBJECT IDENTIFIER
    ::= { cevContainer 206 }

-- logical container for multiple Nexus 5000 or Nexus 7000 switches.  An usage example is when a Nexus 2000 Series Fabric Extender connects into two Nexus 5000 or Nexus 7000 Series switches

cevContainerN2kC2148T1GEPowerSupplyBay  OBJECT IDENTIFIER
    ::= { cevContainer 207 }

-- Container for N2KC2148T-1GE Power Supply bay

cevContainerN2kC2148T1GEFanBay  OBJECT IDENTIFIER
    ::= { cevContainer 208 }

-- Container for N2KC2148T-1GE Fan bay

cevContainerUCSN10S6100FanBay  OBJECT IDENTIFIER
    ::= { cevContainer 209 }

-- 1RU Fabric Chassis Bay for Fan Module

cevContainerUCSN10S6100PowerSupplyBay  OBJECT IDENTIFIER
    ::= { cevContainer 210 }

-- Power Supply Bay for 1RU Fabric Chassis

cevContainerMXE5600PowerSupplyBay  OBJECT IDENTIFIER
    ::= { cevContainer 213 }

-- 6-slot Power supply Bay for Cisco MXE 5600 platform

cevContainerMXE5600FanTray  OBJECT IDENTIFIER
    ::= { cevContainer 214 }

-- Fan Tray for Cisco MXE 5600 platform

cevContainerN2kC2248TP1GEPowerSupplyBay  OBJECT IDENTIFIER
    ::= { cevContainer 218 }

-- Container for N2K-C2248TP-1GE, N3K-C3016,N3K-C3048 and N3K-C3064 Power Supply bay

cevContainerN7Kc7009PowerSupplyBay  OBJECT IDENTIFIER
    ::= { cevContainer 219 }

-- container for Nexus7000 9slot boxster N7Kpowersupply

cevContainerN7KC7009FanBay  OBJECT IDENTIFIER
    ::= { cevContainer 220 }

-- container for Nexus7000 9slot boxster N7K fan

cevContainerFruLinkModuleSlot  OBJECT IDENTIFIER
    ::= { cevContainer 221 }

-- Container for FRULink Modules

cevContainerFlexStackModuleSlot  OBJECT IDENTIFIER
    ::= { cevContainer 222 }

-- Container for Cisco FlexStack Module

cevContainerMXE5600ShelfManagerBay  OBJECT IDENTIFIER
    ::= { cevContainer 223 }

-- Shelf Manager Bay for Cisco MXE 5600 platform

cevContainerMXE5600NpmSlot  OBJECT IDENTIFIER
    ::= { cevContainer 224 }

-- Chassis Slot for NPM module of Cisco MXE 5600 platform

cevContainerMXE5600MpmSlot  OBJECT IDENTIFIER
    ::= { cevContainer 225 }

-- Chassis Slot for MPM module of Cisco MXE 5600 platform

cevContainerN5KC5548FanBay  OBJECT IDENTIFIER
    ::= { cevContainer 226 }

-- Container for N5548P-Fan

cevContainerN5kC5548PowerSupplyBay  OBJECT IDENTIFIER
    ::= { cevContainer 227 }

-- Container for N55-PAC-750W Power supply

cevContainerCrs18PowerShelfVirtual  OBJECT IDENTIFIER
    ::= { cevContainer 228 }

-- Cisco CRS-1 Series Virtual Power Shelf for 8 Slots LCC

cevContainer40GigBasePort  OBJECT IDENTIFIER
    ::= { cevContainer 229 }

-- Generic 40 gigabit ethernet port container

cevContainerSAMBay  OBJECT IDENTIFIER
    ::= { cevContainer 230 }

-- sub-slots in the Integrated Service Module (ISM) where Service Accelerator Module(SAM) Flash cards are inserted

cevContainerN5KC5596FanBay  OBJECT IDENTIFIER
    ::= { cevContainer 231 }

-- Container for N5596UP-Fan

cevContainerN5kC5596PowerSupplyBay  OBJECT IDENTIFIER
    ::= { cevContainer 232 }

-- Container for N55-PAC-1100W Power supply

cevContainerN3KC3064FanBay  OBJECT IDENTIFIER
    ::= { cevContainer 235 }

-- Container for N3K-C3016 and N3K-C3064 Fan

cevContainerUCS6248FanBay  OBJECT IDENTIFIER
    ::= { cevContainer 236 }

-- Container for UCS-FAN-6248UP

cevContainerUCS6248PowerSupplyBay  OBJECT IDENTIFIER
    ::= { cevContainer 237 }

-- Container for UCS-PSU-6248UP Power

cevContainerUCS6296FanBay  OBJECT IDENTIFIER
    ::= { cevContainer 238 }

-- Container for UCS-FAN-6296UP

cevContainerUCS6296PowerSupplyBay  OBJECT IDENTIFIER
    ::= { cevContainer 239 }

-- Container for UCS-PSU-6296UP Power

cevContainerDIMM8541Slot  OBJECT IDENTIFIER
    ::= { cevContainer 240 }

-- DIMM slot for Oe8541

cevContainerDIMM7571Slot  OBJECT IDENTIFIER
    ::= { cevContainer 241 }

-- DIMM slot for Oe7571

cevContainerDIMM7541Slot  OBJECT IDENTIFIER
    ::= { cevContainer 242 }

-- DIMM slot for Oe7541

cevContainerDIMM694Slot  OBJECT IDENTIFIER
    ::= { cevContainer 243 }

-- DIMM slot for Oe694

cevContainerDIMM594Slot  OBJECT IDENTIFIER
    ::= { cevContainer 244 }

-- DIMM slot for Oe594

cevContainerDIMM294Slot  OBJECT IDENTIFIER
    ::= { cevContainer 245 }

-- DIMM slot for Oe294

cevContainerASR900RSPSlot  OBJECT IDENTIFIER
    ::= { cevContainer 246 }

-- ASR 900 Series Route Switch Processor Module Container

cevContainerASR900PowerSupplyBay  OBJECT IDENTIFIER
    ::= { cevContainer 247 }

-- ASR 900 Series Power Supply Module container

cevContainerASR900FanTrayBay  OBJECT IDENTIFIER
    ::= { cevContainer 248 }

-- ASR 900 Series Fan Tray container

cevContainerIMBay  OBJECT IDENTIFIER
    ::= { cevContainer 249 }

-- Represents Interface Module bays on the ASR 900 series

cevContainerN7Kc7004FanBay  OBJECT IDENTIFIER
    ::= { cevContainer 250 }

-- container for Nexus7000 4slot zonda n7k fan

cevContainerN7Kc7004PowerSupplyBay  OBJECT IDENTIFIER
    ::= { cevContainer 251 }

-- container for Nexus7000 4slot zonda n7k powersupply

cevContainerN3KC3048FanBay  OBJECT IDENTIFIER
    ::= { cevContainer 252 }

-- Container for N3K-C3048-Fan

cevContainerN6kC6004FanBay  OBJECT IDENTIFIER
    ::= { cevContainer 262 }

-- Container for N6K-C6004-96Q Fan

cevContainerN6kC6004PowerSupplyBay  OBJECT IDENTIFIER
    ::= { cevContainer 263 }

-- Container for N6K-C6004-96Q Power

cevContainerASR9KSwitchFabricSlot  OBJECT IDENTIFIER
    ::= { cevContainer 264 }

-- Cisco ASR9K Switch Fabric Module Container

cevContainerCFP  OBJECT IDENTIFIER
    ::= { cevContainer 265 }

-- CFP container

cevContainerISR4400NIMSlot  OBJECT IDENTIFIER
    ::= { cevContainer 266 }

-- Cisco ISR 4400 Series Network Interface Module Container

cevContainerISR4400PVDMSlot  OBJECT IDENTIFIER
    ::= { cevContainer 267 }

-- Cisco ISR 4400 Series Packet Voice DSP Module Container

cevContainerISR4400ESMSlot  OBJECT IDENTIFIER
    ::= { cevContainer 268 }

-- Cisco ISR 4400 Series Enhanced Service Module Container

cevContainerISR4400PSBay  OBJECT IDENTIFIER
    ::= { cevContainer 269 }

-- Cisco ISR 4400 Series Power Supply Module Container

cevContainerISR4400FanTrayBay  OBJECT IDENTIFIER
    ::= { cevContainer 270 }

-- Cisco ISR 4400 Series Fan Tray Container

cevContainerISR4400POEBay  OBJECT IDENTIFIER
    ::= { cevContainer 271 }

-- ISR 4400 Series Power Over Ethennet bay

cevContainerISR4400InternalPOEBay  OBJECT IDENTIFIER
    ::= { cevContainer 272 }

-- ISR 4400 Series Internal Power Over Ethennet bay

cevContainerDSC9710FanBay  OBJECT IDENTIFIER
    ::= { cevContainer 273 }

-- Fan Bay for MDS 10-Slot Director Switch, DS9710

cevContainerMDS9250iFanBay  OBJECT IDENTIFIER
    ::= { cevContainer 274 }

-- Fan Bay unit for MDS 9250i Intelligent Fabric Switch

cevContainerN77c7718PowerSupplyBay  OBJECT IDENTIFIER
    ::= { cevContainer 282 }

-- Container for Nexus7700 18-slot power supply

cevContainerN77c7710PowerSupplyBay  OBJECT IDENTIFIER
    ::= { cevContainer 283 }

-- Container for Nexus7700 10-slot power supply

cevContainerN77c7718FanBay  OBJECT IDENTIFIER
    ::= { cevContainer 285 }

-- Container for Nexus7700 18-slot fan

cevContainerN77c7710FanBay  OBJECT IDENTIFIER
    ::= { cevContainer 286 }

-- Container for Nexus7700 10-slot fan

cevContainerQIron22Qzinc2  OBJECT IDENTIFIER
    ::= { cevContainer 292 }

-- QuickIron2/QuickZinc2 Fan Bay

cevContainerDSC9706  OBJECT IDENTIFIER
    ::= { cevContainer 293 }

-- Fan Bay Container for MDS-9706 6-slot Director Switch

cevContainerN9Kc9508FanBay  OBJECT IDENTIFIER
    ::= { cevContainer 301 }

-- container for Nexus9508 fan tray

cevContainerN9Kc9508PowerSupplyBay  OBJECT IDENTIFIER
    ::= { cevContainer 302 }

-- container for Nexus9508 powersupply

cevContainerASR5000SPCSlot  OBJECT IDENTIFIER
    ::= { cevContainer 303 }

-- ASR5000 Service processor card slot for SPC/SMC card types

cevContainerASR5000PTACSlot  OBJECT IDENTIFIER
    ::= { cevContainer 304 }

-- ASR5000 Packet Telephony Accelerator slot for Packet Processor Cards(PPC) or (Packet Accelerator Cards(PAC) or Packet Services Cards(PSC) or Telephony Accelerator Cards(TAC) card types

cevContainerASR5000RCCSlot  OBJECT IDENTIFIER
    ::= { cevContainer 305 }

-- ASR5000 Redundancy Crossbar Card  (RCC)slot for RCC card types

cevContainerASR5000SPIOSlot  OBJECT IDENTIFIER
    ::= { cevContainer 306 }

-- ASR5000 Switch Processor I/O card (SPIO) slot for SPIO card types

cevContainerASR5000LCSlot  OBJECT IDENTIFIER
    ::= { cevContainer 307 }

-- ASR5000 Line card (LC) slot for LC card types

cevContainerASR5000FanTraySlot  OBJECT IDENTIFIER
    ::= { cevContainer 308 }

-- ASR5000 Fan tray slot

cevContainerASR5000PowerSupplySlot  OBJECT IDENTIFIER
    ::= { cevContainer 309 }

-- ASR5000 Power supply slot

cevContainerASR5500MMIOSlot  OBJECT IDENTIFIER
    ::= { cevContainer 310 }

-- ASR5500 Management-mode Management and I/O (MMIO) slot

cevContainerASR5500DPCSlot  OBJECT IDENTIFIER
    ::= { cevContainer 311 }

-- ASR5500 Data Processing Card (DPC) slot

cevContainerASR5500FSCSlot  OBJECT IDENTIFIER
    ::= { cevContainer 312 }

-- ASR5500 Fabric and Storage card(FSC)  slot

cevContainerASR5500SSCSlot  OBJECT IDENTIFIER
    ::= { cevContainer 313 }

-- ASR5500 System Status Card(SSC)  slot

cevContainerASR5500SIOSlot  OBJECT IDENTIFIER
    ::= { cevContainer 314 }

-- ASR5500 Slow-speed I/O Card(SIO)  slot

cevContainerASR5500FanTraySlot  OBJECT IDENTIFIER
    ::= { cevContainer 315 }

-- ASR5500 Fan tray slot

cevContainerASR5500PowerSupplySlot  OBJECT IDENTIFIER
    ::= { cevContainer 316 }

-- ASR5500 Power supply slot

cevContainerDSC48SFAN  OBJECT IDENTIFIER
    ::= { cevContainer 317 }

-- Fan bay unit for MDS 9148 16G Fabric Switch

cevContainerN9KC9300FanBay2  OBJECT IDENTIFIER
    ::= { cevContainer 320 }

-- Container for 3RU Fans

cevContainerN9KC9300FanBay1  OBJECT IDENTIFIER
    ::= { cevContainer 321 }

-- Container for 2RU Fans

cevPowerSupply  OBJECT IDENTIFIER
    ::= { cevMIBObjects 6 }

cevPowerSupplyAC1360W  OBJECT IDENTIFIER
    ::= { cevPowerSupply 1 }

cevPowerSupplyDC1360W  OBJECT IDENTIFIER
    ::= { cevPowerSupply 2 }

cevPowerSupplyAC1000W  OBJECT IDENTIFIER
    ::= { cevPowerSupply 3 }

cevPowerSupplyDC1000W  OBJECT IDENTIFIER
    ::= { cevPowerSupply 4 }

cevPowerSupplyPowerone  OBJECT IDENTIFIER
    ::= { cevPowerSupply 5 }

cevPowerSupplyAstec  OBJECT IDENTIFIER
    ::= { cevPowerSupply 6 }

cevPowerSupplyMinus48VDC  OBJECT IDENTIFIER
    ::= { cevPowerSupply 7 }

cevPowerSupplyEmpty  OBJECT IDENTIFIER
    ::= { cevPowerSupply 8 }

-- Power Supply is Not Present

cevPowerSupplyAC1100W  OBJECT IDENTIFIER
    ::= { cevPowerSupply 9 }

-- Alternating Current, 1100 Watts

cevPowerSupplyAC1200W  OBJECT IDENTIFIER
    ::= { cevPowerSupply 10 }

-- Alternating Current, 1200 Watts

cevPowerSupplyDC1200W  OBJECT IDENTIFIER
    ::= { cevPowerSupply 11 }

-- Direct Current, 1200 Watts

cevPowerSupplyPem  OBJECT IDENTIFIER
    ::= { cevPowerSupply 12 }

-- Cisco 6400 power supply

cevPowerSupplyAC2000W  OBJECT IDENTIFIER
    ::= { cevPowerSupply 13 }

-- Cisco Catalyst 8540MSR power supply

cevPowerSupplyDC2000W  OBJECT IDENTIFIER
    ::= { cevPowerSupply 14 }

-- Cisco Catalyst 8540MSR power supply

cevPowerSupply6260DC  OBJECT IDENTIFIER
    ::= { cevPowerSupply 15 }

-- Cisco 6260 DC Power Entry Module

cevPowerSupply6260AC  OBJECT IDENTIFIER
    ::= { cevPowerSupply 16 }

-- Cisco 6260 AC Power Entry Module

cevPowerSupplyMGX8800Pem  OBJECT IDENTIFIER
    ::= { cevPowerSupply 17 }

-- Cisco MGX8800 Universal Chassis DC Power Entry Modules

cevPowerSupply12012DC  OBJECT IDENTIFIER
    ::= { cevPowerSupply 18 }

-- Cisco 12012 DC Power supply Module

cevPowerSupply12012AC  OBJECT IDENTIFIER
    ::= { cevPowerSupply 19 }

-- Cisco 12012 AC Power supply Module

cevPowerSupply12008DC  OBJECT IDENTIFIER
    ::= { cevPowerSupply 20 }

-- Cisco 12008 DC Power supply Module

cevPowerSupply12008AC  OBJECT IDENTIFIER
    ::= { cevPowerSupply 21 }

-- Cisco 12008 AC Power supply Module

cevPowerSupplyDC2500W  OBJECT IDENTIFIER
    ::= { cevPowerSupply 22 }

-- Cisco 2500 Watt DC power supply for Catalyst 6000 or 8500 series

cevPowerSupplyAC1050W  OBJECT IDENTIFIER
    ::= { cevPowerSupply 23 }

-- Cisco 1050 Watt AC power supply for assorted MGX and IGX series chassis

cevPowerSupplyAC2500W  OBJECT IDENTIFIER
    ::= { cevPowerSupply 24 }

-- Cisco 2500 Watt DC power supply for Catalyst 6000 or 8500 series

cevPowerSupply6160DC  OBJECT IDENTIFIER
    ::= { cevPowerSupply 25 }

-- Cisco 6160 DC power supply module

cevPowerSupplyAC4000W  OBJECT IDENTIFIER
    ::= { cevPowerSupply 28 }

-- Cisco 4000 Watt AC power supply for Catalyst 6000

cevPowerSupplyDC4000W  OBJECT IDENTIFIER
    ::= { cevPowerSupply 29 }

-- Cisco 4000 Watt DC power supply for Catalyst 6000

cevPowerSupply12010DC  OBJECT IDENTIFIER
    ::= { cevPowerSupply 31 }

-- Cisco 12010 DC Power supply Module

cevPowerSupply12010AC  OBJECT IDENTIFIER
    ::= { cevPowerSupply 32 }

-- Cisco 12010 AC Power supply Module

cevPowerSupply5850DC  OBJECT IDENTIFIER
    ::= { cevPowerSupply 33 }

-- Cisco DC power supply for NAS 5850

cevPowerSupply12406DC  OBJECT IDENTIFIER
    ::= { cevPowerSupply 34 }

-- Cisco 12406 DC Power supply Module

cevPowerSupply12406AC  OBJECT IDENTIFIER
    ::= { cevPowerSupply 35 }

-- Cisco 12406 AC Power supply Module

cevPowerSupply12410DC  OBJECT IDENTIFIER
    ::= { cevPowerSupply 36 }

-- Cisco 12410 DC Power supply Module

cevPowerSupply12410AC  OBJECT IDENTIFIER
    ::= { cevPowerSupply 37 }

-- Cisco 12410 AC Power supply Module

cevPowerSupplyAC1900W  OBJECT IDENTIFIER
    ::= { cevPowerSupply 38 }

-- Cisco 1900 watt AC Power Supply

cevPowerSupplyDC1900W  OBJECT IDENTIFIER
    ::= { cevPowerSupply 39 }

-- Cisco 1900 watt DC Power Supply

cevPowerSupplyDC950W  OBJECT IDENTIFIER
    ::= { cevPowerSupply 40 }

-- Cisco 950 watt DC Power Supply

cevPowerSupplyAC950W  OBJECT IDENTIFIER
    ::= { cevPowerSupply 41 }

-- Cisco 950 watt AC Power Supply

cevPowerSupply12404DC  OBJECT IDENTIFIER
    ::= { cevPowerSupply 42 }

-- Cisco 12404 DC Power supply Module

cevPowerSupply12404AC  OBJECT IDENTIFIER
    ::= { cevPowerSupply 43 }

-- Cisco 12404 AC Power supply Module

cevPowerSupplyBP7513AC1200W  OBJECT IDENTIFIER
    ::= { cevPowerSupply 44 }

-- 1200W AC power supply

cevPowerSupplyBP7513DC1200W  OBJECT IDENTIFIER
    ::= { cevPowerSupply 45 }

-- 1200W DC power supply

cevPowerSupplyBP7505AC600W  OBJECT IDENTIFIER
    ::= { cevPowerSupply 46 }

-- 600W AC power supply

cevPowerSupplyBP7505DC600W  OBJECT IDENTIFIER
    ::= { cevPowerSupply 47 }

-- 600W DC power supply

cevPowerSupplyBP7507AC700W  OBJECT IDENTIFIER
    ::= { cevPowerSupply 48 }

-- 700W AC power supply

cevPowerSupplyBP7507DC700W  OBJECT IDENTIFIER
    ::= { cevPowerSupply 49 }

-- 700W DC power supply

cevPowerSupplyAC1900W6  OBJECT IDENTIFIER
    ::= { cevPowerSupply 50 }

-- Cisco 1900 Watt AC Power Supply (pwr1900ac/6)

cevPowerSupplyC7300AC  OBJECT IDENTIFIER
    ::= { cevPowerSupply 51 }

-- Cisco 7300 AC Power Supply

cevPowerSupplyC7300DC  OBJECT IDENTIFIER
    ::= { cevPowerSupply 52 }

-- Cisco 7300 DC Power Supply

cevPowerSupplyAC600W  OBJECT IDENTIFIER
    ::= { cevPowerSupply 53 }

-- Cisco 600 Watt AC Power Supply

cevPowerSupplyDC600W  OBJECT IDENTIFIER
    ::= { cevPowerSupply 54 }

-- Cisco 600 Watt DC Power Supply

cevPowerSupplyC10KDC  OBJECT IDENTIFIER
    ::= { cevPowerSupply 55 }

-- Cisco 10000 DC Power Supply

cevPowerSupplyC10KAC  OBJECT IDENTIFIER
    ::= { cevPowerSupply 56 }

-- Cisco 10000 AC Power Supply

cevPowerSupply15530AC  OBJECT IDENTIFIER
    ::= { cevPowerSupply 59 }

-- Cisco ONS 15530 120-240 VAC Power Supply

cevPowerSupply15530DC  OBJECT IDENTIFIER
    ::= { cevPowerSupply 60 }

-- Cisco ONS 15530 -48 VDC Power Supply

cevPowerSupplyAC3000W  OBJECT IDENTIFIER
    ::= { cevPowerSupply 61 }

-- 3000 watt supply AC

cevPowerSupply12016DC  OBJECT IDENTIFIER
    ::= { cevPowerSupply 63 }

-- Cisco 12016 DC Power supply Module

cevPowerSupply12016AC  OBJECT IDENTIFIER
    ::= { cevPowerSupply 64 }

-- Cisco 12016 AC Power supply Module

cevPowerSupplyDC3000W  OBJECT IDENTIFIER
    ::= { cevPowerSupply 70 }

-- 3000 watt supply DC

cevPowerSupplyCat3750AC50W12V  OBJECT IDENTIFIER
    ::= { cevPowerSupply 71 }

-- Cisco Catalyst 3750 AC power Supply  50 Watt, 12V DC

cevPowerSupplyCat3750AC102W12V  OBJECT IDENTIFIER
    ::= { cevPowerSupply 72 }

-- Cisco Catalyst 3750 AC power Supply  102 Watt, 12V DC

cevPowerSupplyCat3750AC204W12V  OBJECT IDENTIFIER
    ::= { cevPowerSupply 73 }

-- Cisco Catalyst 3750 AC power Supply  204 Watt, 12V DC

cevPowerSupplyCat3750AC252W12V  OBJECT IDENTIFIER
    ::= { cevPowerSupply 74 }

-- Cisco Catalyst 3750 AC power Supply  252 Watt, 12V DC

cevPowerSupplyDsCac2500W  OBJECT IDENTIFIER
    ::= { cevPowerSupply 76 }

-- DS-CAC-2500W     -  2500W AC Power Supply

cevPowerSupplyRedDsCac2500W  OBJECT IDENTIFIER
    ::= { cevPowerSupply 77 }

-- DS-CAC-2500W/2  -  Redundant 2500W AC Power

cevPowerSupplyDsCdc2500W  OBJECT IDENTIFIER
    ::= { cevPowerSupply 78 }

-- DS-CDC-2500W     -  2500W DC Power Supply

cevPowerSupplyRedDsCdc2500W  OBJECT IDENTIFIER
    ::= { cevPowerSupply 79 }

-- DS-CDC-2500W/2   -  Redundant 2500W DC Power

cevPowerSupplyDsCac4000WUs  OBJECT IDENTIFIER
    ::= { cevPowerSupply 80 }

-- DS-CAC-4000W-US    -  4000Watt AC Power Supply for US (cable attached)

cevPowerSupplyRedDsCac4000WUs  OBJECT IDENTIFIER
    ::= { cevPowerSupply 81 }

-- DS-CAC-4000W-US/2    -  Redundant 4000Watt AC Power Supply for US (cable attached)

cevPowerSupplyDsCac4000WInt  OBJECT IDENTIFIER
    ::= { cevPowerSupply 82 }

-- DS-CAC-4000W-INT    -  4000Watt AC Power Supply International (cable attached)

cevPowerSupplyRedDsCac4000WInt  OBJECT IDENTIFIER
    ::= { cevPowerSupply 83 }

-- DS-CAC-4000W-INT/2  -  Redundant 4000W AC Power Supply International (cable attached)

cevPowerSupplyDsCac1900W  OBJECT IDENTIFIER
    ::= { cevPowerSupply 84 }

-- DS-CAC-1900W          -  1900W AC Power Supply

cevPowerSupplyRedDsCac1900W  OBJECT IDENTIFIER
    ::= { cevPowerSupply 85 }

-- DS-CAC-1900W/2        -  Redundant 1900W AC Power Supply

cevPowerSupplyDsCdc1900W  OBJECT IDENTIFIER
    ::= { cevPowerSupply 86 }

-- DS-CDC-1900W          -  1900W DC Power Supply

cevPowerSupplyRedDsCdc1900W  OBJECT IDENTIFIER
    ::= { cevPowerSupply 87 }

-- DS-CDC-1900W/2        -  Redundant 1900W DC Power Supply

cevPowerSupplyRedDsCac845W  OBJECT IDENTIFIER
    ::= { cevPowerSupply 88 }

-- DS-CAC-845W/2  -  redundant MDS 9216 AC Power Supply - 845W

cevPowerSupplyDsCac845W  OBJECT IDENTIFIER
    ::= { cevPowerSupply 89 }

-- DS-CAC-845W  -  MDS 9216 AC Power Supply - 845

cevPowerSupplyUnknown  OBJECT IDENTIFIER
    ::= { cevPowerSupply 90 }

-- Unknown Power supply type

cevPowerSupplyC2970AC156W12V  OBJECT IDENTIFIER
    ::= { cevPowerSupply 91 }

-- Cisco Catalyst 2970 AC power Supply  156 Watt, 12V DC

cevPowerSupplyAc150W  OBJECT IDENTIFIER
    ::= { cevPowerSupply 92 }

-- Cisco 150W AC power supply

cevPowerSupplyC7200AC  OBJECT IDENTIFIER
    ::= { cevPowerSupply 93 }

-- Cisco 7200 AC power supply

cevPowerSupplyC7200DC  OBJECT IDENTIFIER
    ::= { cevPowerSupply 94 }

-- Cisco 7200 DC power supply

cevPowerSupplyAc465W  OBJECT IDENTIFIER
    ::= { cevPowerSupply 95 }

-- Cisco 465W AC Power Supply

cevPowerSupplyDsCac300W  OBJECT IDENTIFIER
    ::= { cevPowerSupply 96 }

-- DS-CAC-300W - 300W AC Power Supply

cevPowerSupplyRedDsCac300W  OBJECT IDENTIFIER
    ::= { cevPowerSupply 97 }

-- DS-CAC-300W/2 - 300W AC Power Supply (Redundant)

cevPowerSupplyAc1400W  OBJECT IDENTIFIER
    ::= { cevPowerSupply 98 }

-- Cisco 1400 Watt AC Power Supply

cevPowerSupplyC2970AC204W12V  OBJECT IDENTIFIER
    ::= { cevPowerSupply 99 }

-- Cisco Catalyst 2970 AC power Supply 204 Watt, 12V DC

cevPowerSupplyCrs1PowerSupply  OBJECT IDENTIFIER
    ::= { cevPowerSupply 100 }

-- Cisco CRS1 Power Supply.

cevPowerSupplyCrs1PowerZone  OBJECT IDENTIFIER
    ::= { cevPowerSupply 101 }

-- Cisco CRS1 Power Zones.

cevPowerSupplyAC6000W  OBJECT IDENTIFIER
    ::= { cevPowerSupply 102 }

-- Cisco 6000 watt AC power supply for Catalyst 6000/6500

cevPowerSupplyDc150W  OBJECT IDENTIFIER
    ::= { cevPowerSupply 103 }

-- Cisco 150W DC Power Supply

cevPowerSupplyAC2700W  OBJECT IDENTIFIER
    ::= { cevPowerSupply 104 }

-- Cisco 2700W AC Power Supply

cevPowerSupplyDC2700W  OBJECT IDENTIFIER
    ::= { cevPowerSupply 105 }

-- Cisco 2700W DC Power Supply

cevPowerSupplyPwrC45300AC  OBJECT IDENTIFIER
    ::= { cevPowerSupply 106 }

-- Catalyst 4000 PWR-C45-300AC power supply module

cevPowerSupplyPwrC45300DC  OBJECT IDENTIFIER
    ::= { cevPowerSupply 107 }

-- Catalyst 4000 PWR-C45-300DC power supply module

cevPowerSupplyAC2900WE  OBJECT IDENTIFIER
    ::= { cevPowerSupply 108 }

-- Cisco 2900W Power supply eith floating power capability for 6503/-E

cevPowerSupplyAC6000WE  OBJECT IDENTIFIER
    ::= { cevPowerSupply 109 }

-- Cisco 6000 watt AC power supply with 52V floating output for Catalyst 6000/6500

cevPowerSupplyAC8700WE  OBJECT IDENTIFIER
    ::= { cevPowerSupply 110 }

-- Cisco 8700 watt AC power supply with 52V floating output for Catalyst 6000/6500

cevPowerSupplyPWR2700AC4  OBJECT IDENTIFIER
    ::= { cevPowerSupply 111 }

-- 2700 watt supply AC(PWR-2700-AC/4)

cevPowerSupplyPWR2700DC4  OBJECT IDENTIFIER
    ::= { cevPowerSupply 112 }

-- 2700 watt supply DC(PWR-2700-AC/4)

cevPowerSupplyPWRC49AC300W  OBJECT IDENTIFIER
    ::= { cevPowerSupply 113 }

-- Catalyst 4000 PWR-C49-300AC power supply module

cevPowerSupplyPWRC49DC300W  OBJECT IDENTIFIER
    ::= { cevPowerSupply 114 }

-- Catalyst 4000 PWR-C49-300DC power supply module

cevPowerSupplyGSR6PemAC  OBJECT IDENTIFIER
    ::= { cevPowerSupply 115 }

-- Cisco 12000 6-slot Enhanced AC PEM

cevPowerSupplyGSR6PemDC  OBJECT IDENTIFIER
    ::= { cevPowerSupply 116 }

-- Cisco 12000 6-slot Enhanced DC PEM

cevPowerSupplyGSR10PemAC  OBJECT IDENTIFIER
    ::= { cevPowerSupply 117 }

-- Cisco 12000 10-slot Enhanced AC PEM

cevPowerSupplyGSR10PemDC  OBJECT IDENTIFIER
    ::= { cevPowerSupply 118 }

-- Cisco 12000 10-slot Enhanced DC PEM

cevPowerSupplyGSR4PemAC  OBJECT IDENTIFIER
    ::= { cevPowerSupply 119 }

-- Cisco 12000 4-slot AC PEM

cevPowerSupplyGSR4PemDC  OBJECT IDENTIFIER
    ::= { cevPowerSupply 120 }

-- Cisco 12000 4-slot DC PEM

cevPowerSupplyGSR16PemAC  OBJECT IDENTIFIER
    ::= { cevPowerSupply 121 }

-- Cisco 12000 16-slot Enhanced AC PEM

cevPowerSupplyGSR16PemDC  OBJECT IDENTIFIER
    ::= { cevPowerSupply 122 }

-- Cisco 12000 16-slot Enhanced DC PEM

cevPowerSupplyC451400DCSP  OBJECT IDENTIFIER
    ::= { cevPowerSupply 123 }

-- Catalyst 4500 1400W DC Power Supply for Service Providers

cevPowerSupplyAc125W  OBJECT IDENTIFIER
    ::= { cevPowerSupply 124 }

-- Cisco 125W AC Power Supply

cevPowerSupplyAc60W  OBJECT IDENTIFIER
    ::= { cevPowerSupply 125 }

-- Cisco 60W AC Power Supply

cevPowerSupplyC454200ACv  OBJECT IDENTIFIER
    ::= { cevPowerSupply 126 }

-- Catalyst 4500  PWR-C45-4200ACV power supply module

cevPowerSupply400wDC  OBJECT IDENTIFIER
    ::= { cevPowerSupply 127 }

-- Catalyst 6524 PWR-400W-DC power supply

cevPowerSupplyEnh12404AC  OBJECT IDENTIFIER
    ::= { cevPowerSupply 128 }

-- Cisco 12404 Enhanced AC Power supply module

cevPowerSupplyEnh12404DC  OBJECT IDENTIFIER
    ::= { cevPowerSupply 129 }

-- Cisco 12404 Enhanced DC Power supply module

cevPowerSupplyEnh12406AC  OBJECT IDENTIFIER
    ::= { cevPowerSupply 130 }

-- Cisco 12406 Enhanced AC Power supply module

cevPowerSupplyEnh12406DC  OBJECT IDENTIFIER
    ::= { cevPowerSupply 131 }

-- Cisco 12406 Enhanced DC Power supply module

cevPowerSupplyEnh12410AC  OBJECT IDENTIFIER
    ::= { cevPowerSupply 132 }

-- Cisco 12410 Enhanced AC Power supply module

cevPowerSupplyEnh12410DC  OBJECT IDENTIFIER
    ::= { cevPowerSupply 133 }

-- Cisco 12410 Enhanced DC Power supply module

cevPowerSupplyEnh12416AC  OBJECT IDENTIFIER
    ::= { cevPowerSupply 134 }

-- Cisco 12416 Enhanced AC Power supply module

cevPowerSupplyEnh12416DC  OBJECT IDENTIFIER
    ::= { cevPowerSupply 135 }

-- Cisco 12416 Enhanced DC Power supply module

cevPowerSupply76xxDC2500W  OBJECT IDENTIFIER
    ::= { cevPowerSupply 136 }

-- Cisco 2500 watt DC power supply for CISCO 76xx

cevPowerSupply76xxAC3000W  OBJECT IDENTIFIER
    ::= { cevPowerSupply 137 }

-- Cisco 3000 watt AC power supply for CISCO 76xx

cevPowerSupply76xxAC4000US  OBJECT IDENTIFIER
    ::= { cevPowerSupply 138 }

-- Cisco 4000 watt AC North America power supply for CISCO 76xx

cevPowerSupply76xxAC4000INT  OBJECT IDENTIFIER
    ::= { cevPowerSupply 139 }

-- Cisco 4000 watt AC International power supply for CISCO 76xx

cevPowerSupply76xxAC6000W  OBJECT IDENTIFIER
    ::= { cevPowerSupply 140 }

-- Cisco 6000 watt AC power supply for CISCO 76xx

cevPowerSupplyDC100W  OBJECT IDENTIFIER
    ::= { cevPowerSupply 141 }

-- Cisco 100 Watt DC power supply

cevPowerSupplyDsCAD6000W  OBJECT IDENTIFIER
    ::= { cevPowerSupply 144 }

-- 6000W AC Power Supply

cevPowerSupplyCat2960AC60W12V  OBJECT IDENTIFIER
    ::= { cevPowerSupply 145 }

-- Cisco Catalyst 2960 AC power Supply 60 Watt, 12V DC

cevPowerSupplyCat2960AC125W12V  OBJECT IDENTIFIER
    ::= { cevPowerSupply 146 }

-- Cisco Catalyst 2960 AC power Supply 125 Watt, 12V DC

cevPowerSupplyCat2960AC210W12V  OBJECT IDENTIFIER
    ::= { cevPowerSupply 147 }

-- Cisco Catalyst 2960 AC power Supply 210 Watt, 12V DC

cevPowerSupply6340PWRDC  OBJECT IDENTIFIER
    ::= { cevPowerSupply 148 }

-- ME6340 147 watt DC Power Supply

cevPowerSupply6340PWRAC  OBJECT IDENTIFIER
    ::= { cevPowerSupply 149 }

-- ME6340 147 watt AC Power Supply

cevPowerSupplyUbr10012AC  OBJECT IDENTIFIER
    ::= { cevPowerSupply 150 }

-- UBR10012 Series AC Power Entry Module

cevPowerSupplyUbr10012DC  OBJECT IDENTIFIER
    ::= { cevPowerSupply 151 }

-- UBR10012 Series DC Power Entry Module

cevPowerSupply400wAC  OBJECT IDENTIFIER
    ::= { cevPowerSupply 152 }

-- Catalyst 6524 PWR-400W-AC power supply

cevPowerSupplyCE500AC60W12V  OBJECT IDENTIFIER
    ::= { cevPowerSupply 153 }

-- Cisco Catalyst Express 500 AC power Supply 60 Watt, 12V DC

cevPowerSupplyCE500AC375W48V  OBJECT IDENTIFIER
    ::= { cevPowerSupply 154 }

-- Cisco Catalyst Express 500 AC power Supply 375 Watt, 48V DC

cevPowerSupplyCE500AC75W48V  OBJECT IDENTIFIER
    ::= { cevPowerSupply 155 }

-- Cisco Catalyst Express 500 AC power Supply 75 Watt, 48V DC

cevPowerSupplyCE500AC168W12V  OBJECT IDENTIFIER
    ::= { cevPowerSupply 156 }

-- Cisco Catalyst Express 500 AC power Supply 168 Watt, 12V DC

cevPowerSupplyCat3750AC210W12V  OBJECT IDENTIFIER
    ::= { cevPowerSupply 157 }

-- Cisco Catalyst 3750 AC power Supply  210 Watt, 12V DC

cevPowerSupplyCat3750AC375W48V  OBJECT IDENTIFIER
    ::= { cevPowerSupply 158 }

-- Cisco Catalyst 3750 AC power Supply  375 Watt, -48V DC

cevPowerSupplyAC50W  OBJECT IDENTIFIER
    ::= { cevPowerSupply 159 }

-- Cisco 50W AC power supply

cevPowerSupplyDC50W  OBJECT IDENTIFIER
    ::= { cevPowerSupply 160 }

-- Cisco 50W DC power supply

cevPowerSupplyCrs116PowerShelfACDelta  OBJECT IDENTIFIER
    ::= { cevPowerSupply 161 }

-- Cisco CRS-1 Series AC Delta Power Shelf for 16 Slots Line Card Chassis

cevPowerSupplyCrs116PowerShelfACWye  OBJECT IDENTIFIER
    ::= { cevPowerSupply 162 }

-- Cisco CRS-1 Series AC Wye Power Shelf for 16 Slots Line Card Chassis

cevPowerSupplyCrs116PowerShelfDC  OBJECT IDENTIFIER
    ::= { cevPowerSupply 163 }

-- Cisco CRS-1 Series DC Power Shelf for 16 Slots Line Card Chassis

cevPowerSupplyCrs116ACRectifier  OBJECT IDENTIFIER
    ::= { cevPowerSupply 164 }

-- Cisco CRS-1 Series AC Power Rectifier for 16 Slot Line Card Chassis and Fabric Card Chassis

cevPowerSupplyCrs116DCPEM  OBJECT IDENTIFIER
    ::= { cevPowerSupply 165 }

-- Cisco CRS-1 Series DC Power Entry Module for 16 Slot Line Card Chassis and Fabric Card Chassis

cevPowerSupplyDsCac3000W  OBJECT IDENTIFIER
    ::= { cevPowerSupply 167 }

-- Cisco MDS 9513 Power Supply - DS-CAC-3000W

cevPowerSupplyPWR6000DC  OBJECT IDENTIFIER
    ::= { cevPowerSupply 168 }

-- 6000W DC Power Supply

cevPowerSupplyCrs18ACRectifier  OBJECT IDENTIFIER
    ::= { cevPowerSupply 169 }

-- Cisco CRS-1 Series AC Power Rectifier for 8 slot LCC

cevPowerSupplyCrs18DCPem  OBJECT IDENTIFIER
    ::= { cevPowerSupply 170 }

-- Cisco CRS-1 Series DC Power Entry Module for 8 slot LCC

cevPowerSupplyCrs18ACDelta  OBJECT IDENTIFIER
    ::= { cevPowerSupply 171 }

-- Cisco CRS-1 Series 8 Slot LCC with Redundant AC Delta Power

cevPowerSupplyCrs18ACW  OBJECT IDENTIFIER
    ::= { cevPowerSupply 172 }

-- Cisco CRS-1 Series 8 Slot LCC with Redundant AC Wye Power

cevPowerSupplyCrs18DC  OBJECT IDENTIFIER
    ::= { cevPowerSupply 173 }

-- Cisco CRS-1 Series 8 Slot LCC with Redundant DC Power

cevPowerSupplyCrs18PduACD  OBJECT IDENTIFIER
    ::= { cevPowerSupply 174 }

-- Cisco CRS-1 Series AC Delta PDU for CRS-8 LCC

cevPowerSupplyCrs18PduACW  OBJECT IDENTIFIER
    ::= { cevPowerSupply 175 }

-- Cisco CRS-1 Series AC Wye PDU for CRS-8 LCC

cevPowerSupplyCrs18PduDC  OBJECT IDENTIFIER
    ::= { cevPowerSupply 176 }

-- Cisco CRS-1 Series DC PDU for CRS-8 LCC

cevPowerSupplyCrs1FcACD  OBJECT IDENTIFIER
    ::= { cevPowerSupply 177 }

-- Cisco CRS-1 Fabric Chassis AC Delta Power Supply

cevPowerSupplyCrs1FcACW  OBJECT IDENTIFIER
    ::= { cevPowerSupply 178 }

-- Cisco CRS-1 Fabric Chassis AC Wye Option

cevPowerSupplyCrs1FcDC  OBJECT IDENTIFIER
    ::= { cevPowerSupply 179 }

-- Cisco CRS-1 Fabric Chassis DC Power Option

cevPowerSupplyCrs14PowerShelfAC  OBJECT IDENTIFIER
    ::= { cevPowerSupply 180 }

-- Cisco CRS-1 Series AC Power Shelf for 4 Slots LCC

cevPowerSupplyCrs14PowerShelfDC  OBJECT IDENTIFIER
    ::= { cevPowerSupply 181 }

-- Cisco CRS-1 Series DC Power Shelf for 4 Slots LCC

cevPowerSupplyCrs14PowerSupplyDC  OBJECT IDENTIFIER
    ::= { cevPowerSupply 182 }

-- Cisco CRS-1 Series DC Power Supply for 4 Slots LCC

cevPowerSupplyCrs14PowerSupplyAC  OBJECT IDENTIFIER
    ::= { cevPowerSupply 183 }

-- Cisco CRS-1 Series AC Power Supply for 4 Slots LCC

cevPowerSupplyC3KPWR265WAC  OBJECT IDENTIFIER
    ::= { cevPowerSupply 184 }

-- Catalyst 3K 265 Watt, 12V AC Power Supply

cevPowerSupplyC3KPWR265WDC  OBJECT IDENTIFIER
    ::= { cevPowerSupply 185 }

-- Catalyst 3K 265 Watt, 12V DC Power Supply

cevPowerSupplyC3KPWR750WAC  OBJECT IDENTIFIER
    ::= { cevPowerSupply 186 }

-- Catalyst 3K 750 Watt, 12V/-52V AC Power Supply

cevPowerSupplyCat2960AC36W12V  OBJECT IDENTIFIER
    ::= { cevPowerSupply 188 }

-- Cisco Catalyst 2960 AC power Supply 36 Watt, 12V DC

cevPowerSupplyCat3560AC173W48V  OBJECT IDENTIFIER
    ::= { cevPowerSupply 189 }

-- Cisco Catalyst 3560 AC power Supply 173 Watt, 48V DC

cevPowerSupplyAC345  OBJECT IDENTIFIER
    ::= { cevPowerSupply 190 }

-- AC Power Supply 345 Watts

cevPowerSupplyC3KPWR1150WAC  OBJECT IDENTIFIER
    ::= { cevPowerSupply 191 }

-- Catalyst 3K 1150 Watt, 12V/-52V AC Power Supply

cevPowerSupplyPwrRPS2300  OBJECT IDENTIFIER
    ::= { cevPowerSupply 192 }

-- Cisco Redundant Power System (RPS2300) with 2300 Watt total power

cevPowerSupplyCrs14DcPim  OBJECT IDENTIFIER
    ::= { cevPowerSupply 193 }

-- Cisco CRS-1 Series DC Power Input Module for 4 Slots LCC

cevPowerSupplyDC1500W  OBJECT IDENTIFIER
    ::= { cevPowerSupply 194 }

-- Cisco 1500W DC power supply for CISCO 7603-S

cevPowerSupplyC7201AC  OBJECT IDENTIFIER
    ::= { cevPowerSupply 195 }

-- Cisco 7201 AC power supply

cevPowerSupplyC7201DC  OBJECT IDENTIFIER
    ::= { cevPowerSupply 196 }

-- Cisco 7201 DC power supply

cevPowerSupplyCE520AC173W48V  OBJECT IDENTIFIER
    ::= { cevPowerSupply 197 }

-- Cisco Catalyst Express 520 AC power Supply 173 Watt, 48V DC

cevPowerSupplyAC100W  OBJECT IDENTIFIER
    ::= { cevPowerSupply 198 }

-- Cisco 100 watt AC power supply

cevPowerSupplyN7KAC5600W  OBJECT IDENTIFIER
    ::= { cevPowerSupply 199 }

-- AC 5.6KW powersupply for Nexus7000 N7K

cevPowerSupplyASR1002AC  OBJECT IDENTIFIER
    ::= { cevPowerSupply 200 }

-- Cisco ASR1002 AC Power Supply Module

cevPowerSupplyASR1002DC  OBJECT IDENTIFIER
    ::= { cevPowerSupply 201 }

-- Cisco ASR1002 DC Power Supply Module

cevPowerSupplyASR1004AC  OBJECT IDENTIFIER
    ::= { cevPowerSupply 202 }

-- Cisco ASR1004 AC Power Supply Module

cevPowerSupplyASR1004DC  OBJECT IDENTIFIER
    ::= { cevPowerSupply 203 }

-- Cisco ASR1004 DC Power Supply Module

cevPowerSupplyASR1006AC  OBJECT IDENTIFIER
    ::= { cevPowerSupply 204 }

-- Cisco ASR1006 AC Power Supply Module

cevPowerSupplyASR1006DC  OBJECT IDENTIFIER
    ::= { cevPowerSupply 205 }

-- Cisco ASR1006 DC Power Supply Module

cevPowerSupplyASR1000Unknown  OBJECT IDENTIFIER
    ::= { cevPowerSupply 206 }

-- Cisco ASR1000 Unknown Power Supply Module

cevPowerSupplyC49M1000AC  OBJECT IDENTIFIER
    ::= { cevPowerSupply 207 }

-- Catalyst 4900M PWR-C49M-1000AC power supply module

cevPowerSupplyC49M1000DC  OBJECT IDENTIFIER
    ::= { cevPowerSupply 208 }

-- Catalyst 4900M PWR-C49M-1000DC power supply module

cevPowerSupplyN7KAC7500W  OBJECT IDENTIFIER
    ::= { cevPowerSupply 209 }

-- N7K-AC-7.5KW,  AC 7.5KW powersupply for Nexus7000 N7K

cevPowerSupplyCE520LCAC135W12V  OBJECT IDENTIFIER
    ::= { cevPowerSupply 210 }

-- Cisco Catalyst Express 520 AC power Supply 135 Watt, 12V DC

cevPowerSupplyCE520PCAC558W12V  OBJECT IDENTIFIER
    ::= { cevPowerSupply 211 }

-- Cisco Catalyst Express 520 AC power Supply 558 Watt, 12V DC

cevPowerSupplyCE520TTAC60W12V  OBJECT IDENTIFIER
    ::= { cevPowerSupply 212 }

-- Cisco Catalyst Express 520 AC power Supply 60 Watt, 12V DC

cevPowerSupplyCE520GTCAC125W12V  OBJECT IDENTIFIER
    ::= { cevPowerSupply 213 }

-- Cisco Catalyst Express 520 AC power Supply 125 Watt, 12V DC

cevPowerSupplyN7KAC6000W  OBJECT IDENTIFIER
    ::= { cevPowerSupply 214 }

-- N7K-AC-6.0KW,  AC 6000W powersupply for Nexus7000 N7K

cevPowerSupplyDc4500W  OBJECT IDENTIFIER
    ::= { cevPowerSupply 215 }

-- RF gateway power supply DC 4500 Watts.

cevPowerSupplyIE3000AC  OBJECT IDENTIFIER
    ::= { cevPowerSupply 216 }

-- Cisco Industrial Ethernet Switch IE3000 Power Transformer

cevPowerSupplyN5kPac1200W  OBJECT IDENTIFIER
    ::= { cevPowerSupply 217 }

-- PSU module, A/C, 208v 1200w  for N5020 2RU

cevPowerSupplyCat2918AC60W12V  OBJECT IDENTIFIER
    ::= { cevPowerSupply 218 }

-- Cisco Catalyst 2918 AC power supply 60 Watt, 12V DC

cevPowerSupplyC3KPWR300WAC  OBJECT IDENTIFIER
    ::= { cevPowerSupply 220 }

-- Catalyst 3560E-12D/3560E-12SD 300 Watt AC power supply

cevPowerSupplyC3KPWR300WDC  OBJECT IDENTIFIER
    ::= { cevPowerSupply 221 }

-- Catalyst 3560E-12D/3560E-12SD 300 Watt DC power supply

cevPowerSupplyDCPowerSupply  OBJECT IDENTIFIER
    ::= { cevPowerSupply 222 }

-- Generic DC power supply

cevPowerSupplyACPowerSupply  OBJECT IDENTIFIER
    ::= { cevPowerSupply 223 }

-- Generic AC power supply

cevPowerSupplyN7KAC7500WINT  OBJECT IDENTIFIER
    ::= { cevPowerSupply 228 }

-- N7K-AC-7.5KW-INT AC powersupply for Nexus7000 N7k

cevPowerSupplyN7KAC7500WUS  OBJECT IDENTIFIER
    ::= { cevPowerSupply 229 }

-- N7K-AC-7.5KW-US AC powersupply for Nexus7000 N7K

cevPowerSupplyN5kPac550W  OBJECT IDENTIFIER
    ::= { cevPowerSupply 230 }

-- PSU module, A/C, 208v 1200w for N5K product family

cevPowerSupplyASR9KDC2100W  OBJECT IDENTIFIER
    ::= { cevPowerSupply 231 }

-- 2kW DC Power Module

cevPowerSupplyASR9KDC1500W  OBJECT IDENTIFIER
    ::= { cevPowerSupply 232 }

-- 1.5kW DC Power Module

cevPowerSupplyASR9KAC3KW  OBJECT IDENTIFIER
    ::= { cevPowerSupply 233 }

-- 3kW AC Power Module

cevPowerSupplyCrs16dcPemB  OBJECT IDENTIFIER
    ::= { cevPowerSupply 234 }

-- Cisco CRS-1 16 Slot System Reduced-Noise DC PEM

cevPowerSupplyC3900PWRPOE  OBJECT IDENTIFIER
    ::= { cevPowerSupply 235 }

-- Cisco 3925/3945 AC Power Supply with Power Over Ethernat

cevPowerSupplyC3900PWRAC  OBJECT IDENTIFIER
    ::= { cevPowerSupply 236 }

-- Cisco 3925/3945 AC Power Supply

cevPowerSupplyC2921C2951PWRPOE  OBJECT IDENTIFIER
    ::= { cevPowerSupply 237 }

-- Cisco 2921/2951 AC Power Supply with Power Over Ethernat

cevPowerSupplyC2921C2951PWRAC  OBJECT IDENTIFIER
    ::= { cevPowerSupply 238 }

-- Cisco 2921/2951 AC Power Supply

cevPowerSupplyC2911PWRPOE  OBJECT IDENTIFIER
    ::= { cevPowerSupply 239 }

-- Cisco 2911 AC Power Supply with Power Over Ethernat

cevPowerSupplyC2911PWRAC  OBJECT IDENTIFIER
    ::= { cevPowerSupply 240 }

-- Cisco 2911 AC Power Supply

cevPowerSupplyC2901PWRPOE  OBJECT IDENTIFIER
    ::= { cevPowerSupply 241 }

-- Cisco 2901 AC Power Supply with Power Over Ethernat

cevPowerSupplyC1941C2901PWRAC  OBJECT IDENTIFIER
    ::= { cevPowerSupply 242 }

-- Cisco 2901 AC Power Supply

cevPowerSupplyC1941PWRPOE  OBJECT IDENTIFIER
    ::= { cevPowerSupply 243 }

-- Cisco 1941 AC Power Supply with Power Over Ethernat

cevPowerSupplyC3900PWRDC  OBJECT IDENTIFIER
    ::= { cevPowerSupply 244 }

-- Cisco 3925/3945 DC Power Supply

cevPowerSupplyC2921C2951PWRDC  OBJECT IDENTIFIER
    ::= { cevPowerSupply 245 }

-- Cisco 2921/2951 DC Power Supply

cevPowerSupplyC2911PWRDC  OBJECT IDENTIFIER
    ::= { cevPowerSupply 246 }

-- Cisco 2911 DC power Supply

cevPowerSupplyC2921C2951RPSADPTR  OBJECT IDENTIFIER
    ::= { cevPowerSupply 247 }

-- Cisco 2921/2951 RPS Adaptor for use with External RPS

cevPowerSupplyC2911RPSADPTR  OBJECT IDENTIFIER
    ::= { cevPowerSupply 248 }

-- Cisco 2911 RPS Adaptor for use with External RPS

cevPowerSupplyN2kPac200W  OBJECT IDENTIFIER
    ::= { cevPowerSupply 249 }

-- Nexus 2000 FEX 1GE 200W Power supply

cevPowerSupplyC456000ACV  OBJECT IDENTIFIER
    ::= { cevPowerSupply 250 }

-- 6000W AC power supply for Catalyst 4500 switches

cevPowerUCSN10PAC1550W  OBJECT IDENTIFIER
    ::= { cevPowerSupply 251 }

-- PSU module, A/C, 110/208v 550w  for 20 port interconnect

cevPowerSupplyN7KDC6000W  OBJECT IDENTIFIER
    ::= { cevPowerSupply 253 }

-- N7K-DC-6.0KW,  DC 6000W powersupply for Nexus7000 N7K

cevPowerSupplyCrs18PowerShelfDCModular  OBJECT IDENTIFIER
    ::= { cevPowerSupply 254 }

-- Cisco CRS-1 Series Modular DC Power Shelf for 8 Slots LCC

cevPowerSupplyCrs18PowerShelfACModular  OBJECT IDENTIFIER
    ::= { cevPowerSupply 255 }

-- Cisco CRS-1 Series Modular AC Power Shelf for 8 Slots LCC

cevPowerSupplyCrs116FCCPowerShelfDCModular  OBJECT IDENTIFIER
    ::= { cevPowerSupply 256 }

-- Cisco CRS-1 Series Modular DC Power Shelf for FCC

cevPowerSupplyCrs116FCCPowerShelfACModular  OBJECT IDENTIFIER
    ::= { cevPowerSupply 257 }

-- Cisco CRS-1 Series Modular AC Power Shelf for FCC

cevPowerSupplyCrs1DCPowerModule  OBJECT IDENTIFIER
    ::= { cevPowerSupply 258 }

-- Cisco CRS-1 Series DC Power Module 2100W

cevPowerSupplyCrs1ACPowerModule  OBJECT IDENTIFIER
    ::= { cevPowerSupply 259 }

-- Cisco CRS-1 Series AC Power Module 3000W

cevPowerSupplyCrs116LCCPowerShelfDCModular  OBJECT IDENTIFIER
    ::= { cevPowerSupply 260 }

-- Cisco CRS-1 Series Modular DC Power Shelf for 16 Slots LCC

cevPowerSupplyCrs116LCCPowerShelfACModular  OBJECT IDENTIFIER
    ::= { cevPowerSupply 261 }

-- Cisco CRS-1 Series Modular AC Power Shelf for 16 Slots LCC

cevPowerSupplyCat2960AC123W12V  OBJECT IDENTIFIER
    ::= { cevPowerSupply 262 }

-- Cisco Catalyst 2960 AC power Supply 123 Watt, 12V DC

cevPowerSupplyCat2960AC370W12V  OBJECT IDENTIFIER
    ::= { cevPowerSupply 263 }

-- Cisco Catalyst 2960 AC power Supply 370 Watt, 12V DC

cevPowerSupplyCat2960AC235W12V  OBJECT IDENTIFIER
    ::= { cevPowerSupply 264 }

-- Cisco Catalyst 2960 AC power Supply 235 Watt, 12V DC

cevPowerSupplyCat2960AC525W12V  OBJECT IDENTIFIER
    ::= { cevPowerSupply 265 }

-- Cisco Catalyst 2960 AC power Supply 525 Watt, 12V DC

cevPowerSupplyASR1001AC  OBJECT IDENTIFIER
    ::= { cevPowerSupply 267 }

-- Cisco ASR1001 AC Power Supply

cevPowerSupplyASR1001DC  OBJECT IDENTIFIER
    ::= { cevPowerSupply 268 }

-- Cisco ASR1001 DC Power Supply

cevPowerSupplyASR1013AC  OBJECT IDENTIFIER
    ::= { cevPowerSupply 269 }

-- Cisco ASR1013 AC Power Supply

cevPowerSupplyASR1013DC  OBJECT IDENTIFIER
    ::= { cevPowerSupply 270 }

-- Cisco ASR1013 DC Power Supply

cevPowerSupplyC1941PWRAC  OBJECT IDENTIFIER
    ::= { cevPowerSupply 271 }

-- C1941 AC Power Supply

cevPowerSupplyASR1002DC24V  OBJECT IDENTIFIER
    ::= { cevPowerSupply 272 }

-- Cisco ASR1002 24V DC Power Supply

cevPowerSupplyN2kC2200Pac400W  OBJECT IDENTIFIER
    ::= { cevPowerSupply 273 }

-- N2K-C2200 Series 400W AC Power Supply

cevPowerSupplyC3kxPwr350wAc  OBJECT IDENTIFIER
    ::= { cevPowerSupply 278 }

-- Cisco Catalyst 3750X/3560X 350 Watt AC Power Supply

cevPowerSupplyC3kxPwr715wAc  OBJECT IDENTIFIER
    ::= { cevPowerSupply 279 }

-- Cisco Catalyst 3750X/3560X 715 Watt AC Power Supply

cevPowerSupplyC3kxPwr1100wAc  OBJECT IDENTIFIER
    ::= { cevPowerSupply 280 }

-- Cisco Catalyst 3750X/3560X 1100 Watt AC Power Supply

cevPowerSupplyPWRME3KXAC  OBJECT IDENTIFIER
    ::= { cevPowerSupply 282 }

-- Metro Ethernet 3600X/3800X AC power supply

cevPowerSupplyPWRME3KXDC  OBJECT IDENTIFIER
    ::= { cevPowerSupply 283 }

-- Metro Ethernet 3600X/3800X DC power supply

cevPowerSupplyCGR20xxCGS25xxPWRACPOE  OBJECT IDENTIFIER
    ::= { cevPowerSupply 284 }

-- Cisco Connected Grid Router 20xx/Switch 25xx AC POE Power Supply

cevPowerSupplyCGR20xxCGS25xxPWRDCPOE  OBJECT IDENTIFIER
    ::= { cevPowerSupply 285 }

-- Cisco Connected Grid Router 20xx/Switch 25xx DC POE Power Supply

cevPowerSupplyMXE5600  OBJECT IDENTIFIER
    ::= { cevPowerSupply 286 }

-- Power Supply module for Cisco MXE 5600 platform

cevPowerSupplyC7225AC  OBJECT IDENTIFIER
    ::= { cevPowerSupply 287 }

-- 12V/ 540W output PSU, since the older Marin PSU only can provide 300W power(output), cant support the uBR7225 system with 2 new Bajie boards

cevPowerSupplyPWRC49EAC300WR  OBJECT IDENTIFIER
    ::= { cevPowerSupply 288 }

-- Catalyst 4948E PWR-C49E-300AC-R Power Supply Module

cevPowerSupplyC2360Pwr135wac  OBJECT IDENTIFIER
    ::= { cevPowerSupply 290 }

-- Cisco Catalyst 2360 FRU 135 Watt AC Power Supply

cevPowerSupplyN55Pac750W  OBJECT IDENTIFIER
    ::= { cevPowerSupply 291 }

-- PSU module, A/C, 750W for Nexus 5548 product family

cevPowerSupplyCrs16PshDcB  OBJECT IDENTIFIER
    ::= { cevPowerSupply 293 }

-- CRS Modular DC Power Shelf for CRS-16/S-B

cevPowerSupplyCrs16PshAcB  OBJECT IDENTIFIER
    ::= { cevPowerSupply 294 }

-- CRS Modular AC Power Shelf for CRS-16/S-B

cevPowerSupplyPWRC49EAC300WF  OBJECT IDENTIFIER
    ::= { cevPowerSupply 295 }

-- Catalyst 4948E-F PWR-C49E-300AC-F Power Supply Front exhaust Module

cevPowerSupplyPWRC49DC300WF  OBJECT IDENTIFIER
    ::= { cevPowerSupply 296 }

-- Catalyst 4948E-F PWR-C49-300DC-F Power Supply Front exhaust Module

cevPowerSupplyN2kN2200Pdc400W  OBJECT IDENTIFIER
    ::= { cevPowerSupply 297 }

-- N2200 Series 400W DC Power Supply for 2nd Generation N2K product family

cevPowerSupplyASR1000PS  OBJECT IDENTIFIER
    ::= { cevPowerSupply 298 }

-- Cisco ASR1000 Power Supply in the Power Supply Module

cevPowerSupplyCat2928AC60W12V  OBJECT IDENTIFIER
    ::= { cevPowerSupply 299 }

-- Cisco Catalyst 2928 AC power supply 60 Watt, 12V AC

cevPowerSupplyCat2928AC100W12V  OBJECT IDENTIFIER
    ::= { cevPowerSupply 300 }

-- Cisco Catalyst 2928 AC power supply 100 Watt, 12V or 135 Watt, 50V AC

cevPowerSupplyPwrXPS2200  OBJECT IDENTIFIER
    ::= { cevPowerSupply 301 }

-- Cisco eXpandable Power System (XPS-2200) with 9 dual StackPower and RPS power ports

cevPowerSupplyN55Pac1100W  OBJECT IDENTIFIER
    ::= { cevPowerSupply 302 }

-- PSU module, A/C, 1100W with Front-To-Back airflow for Nexus 5596 product family

cevPowerSupplyN2kN2200Pac400WB  OBJECT IDENTIFIER
    ::= { cevPowerSupply 303 }

-- N2K-C2200, N3K-C3016, N3K-C3048 and N3K-C3064 400W ACPower Supply, Back to Front Airflow

cevPowerSupplyUCS6248UpAC750W  OBJECT IDENTIFIER
    ::= { cevPowerSupply 306 }

-- UCS 6248 750W AC Power Supply

cevPowerSupplyUCS6248UpDC750W  OBJECT IDENTIFIER
    ::= { cevPowerSupply 307 }

-- UCS 6248 750W DC Power Supply

cevPowerSupplyUCS6296UpDC1100W  OBJECT IDENTIFIER
    ::= { cevPowerSupply 308 }

-- UCS 6296 1100W DC Power Supply

cevPowerSupplyUCS6296UpAC1100W  OBJECT IDENTIFIER
    ::= { cevPowerSupply 309 }

-- UCS 6296 1100W AC Power Supply

cevPowerSupplyN7KDC3KW  OBJECT IDENTIFIER
    ::= { cevPowerSupply 310 }

-- N7K-DC-3KW,  DC 3000W Power Supply

cevPowerSupplyCat2960CAC167W  OBJECT IDENTIFIER
    ::= { cevPowerSupply 311 }

-- Cisco Catalyst 2960C AC power Supply, 135W for POE, 38W for System

cevPowerSupplyCat2960CAC36W12V  OBJECT IDENTIFIER
    ::= { cevPowerSupply 312 }

-- Cisco Catalyst 2960C AC power Supply, 0W for POE, 36W for System

cevPowerSupplyN7KAC3KW  OBJECT IDENTIFIER
    ::= { cevPowerSupply 313 }

-- N7K-AC-3KW,  AC 3000W Power Supply

cevPowerSupplyN55Pdc750W  OBJECT IDENTIFIER
    ::= { cevPowerSupply 314 }

-- PSU module, DC, 750W with Back-To-Front airflow for Nexus 5548 product family

cevPowerSupplyOe8541  OBJECT IDENTIFIER
    ::= { cevPowerSupply 315 }

-- Power Supply Module for Oe8541

cevPowerSupplyOe7571  OBJECT IDENTIFIER
    ::= { cevPowerSupply 316 }

-- Power Supply Module for Oe7571

cevPowerSupplyOe7541  OBJECT IDENTIFIER
    ::= { cevPowerSupply 317 }

-- Power Supply Module for Oe7541

cevPowerSupplyOe694  OBJECT IDENTIFIER
    ::= { cevPowerSupply 318 }

-- Power Supply Module for Oe694

cevPowerSupplyOe594  OBJECT IDENTIFIER
    ::= { cevPowerSupply 319 }

-- Power Supply Module for Oe594

cevPowerSupplyOe294  OBJECT IDENTIFIER
    ::= { cevPowerSupply 320 }

-- Power Supply Module for Oe294

cevPowerSupplyASA5555PSInput  OBJECT IDENTIFIER
    ::= { cevPowerSupply 324 }

-- Power Supply unit in Adapative Security Appliance 5555

cevPowerSupplyN2kN2200Pac400W  OBJECT IDENTIFIER
    ::= { cevPowerSupply 325 }

-- N2K-C2200, N3K-C3016, N3K-C3048 and N3K-C3064 400W ACPower Supply, Front to Back Airflow

cevPowerSupplyN55Pac750WB  OBJECT IDENTIFIER
    ::= { cevPowerSupply 326 }

-- PSU module, A/C, 750W with Back-To-Front airflow for Nexus 5548 product family

cevPowerSupplyN55Pac1100WB  OBJECT IDENTIFIER
    ::= { cevPowerSupply 327 }

-- PSU module, A/C, 1100W with Front-to-Back airflow for Nexus 5596 product family

cevPowerSupplyASR900DC500W  OBJECT IDENTIFIER
    ::= { cevPowerSupply 328 }

-- ASR 900 500W DC Power Supply

cevPowerSupplyCrs8PshDcB  OBJECT IDENTIFIER
    ::= { cevPowerSupply 330 }

-- CRS Modular DC Power Shelf for CRS-8/S-B

cevPowerSupplyCrs8PshAcB  OBJECT IDENTIFIER
    ::= { cevPowerSupply 331 }

-- CRS Modular AC Power Shelf for CRS-8/S-B

cevPowerSupplyASR5KPfu  OBJECT IDENTIFIER
    ::= { cevPowerSupply 332 }

-- ASR5000 Power Filter Unit, Non-Redundant, Single 165A

cevPowerSupplyASR55PFU  OBJECT IDENTIFIER
    ::= { cevPowerSupply 333 }

-- ASR5500 Power Filter Unit (PFU)

cevPowerSupplyC459000ACV  OBJECT IDENTIFIER
    ::= { cevPowerSupply 337 }

-- A triple AC (120V/220V) input that provides up to 9000 Watts. This power supply is intended for use on voice enabled Catalyst 4500 series 3, 6, 7, and 10 slot platforms (including the E series models)

cevPowerSupplyN2kN2200Pdc350WB  OBJECT IDENTIFIER
    ::= { cevPowerSupply 338 }

-- N2200 Series 350W DC Power Supply  with Back-To-Front airflow for N2K product family

cevPowerSupplyASR9KAC3KWV2  OBJECT IDENTIFIER
    ::= { cevPowerSupply 341 }

-- 3kW AC Power Module

cevPowerSupplyASR9KDC2100WV2  OBJECT IDENTIFIER
    ::= { cevPowerSupply 342 }

-- 2kW DC Power Module

cevPowerSupplyASR9KAC750W  OBJECT IDENTIFIER
    ::= { cevPowerSupply 343 }

-- ASR-9001 AC Power Supply

cevPowerSupplyASR9KDC750W  OBJECT IDENTIFIER
    ::= { cevPowerSupply 344 }

-- ASR-9001 DC Power Supply

cevPowerSupplyISR4400PWR1000  OBJECT IDENTIFIER
    ::= { cevPowerSupply 345 }

-- Cisco ISR 4400 Series 1000W AC Power Supply

cevPowerSupplyISR4400PWR450  OBJECT IDENTIFIER
    ::= { cevPowerSupply 346 }

-- Cisco ISR 4400 Series 450W AC Power Supply

cevPowerSupplyC4KXPWR750DCF  OBJECT IDENTIFIER
    ::= { cevPowerSupply 347 }

-- Cisco Catalyst C4500X C4KX-PWR-750DC-F 750W DC Power Supply with Back to Front Cooling

cevPowerSupplyC4KXPWR750ACF  OBJECT IDENTIFIER
    ::= { cevPowerSupply 348 }

-- Cisco Catalyst C4500X C4KX-PWR-750AC-F 750W AC Power Supply with Back to Front Cooling

cevPowerSupplyC4KXPWR750DCR  OBJECT IDENTIFIER
    ::= { cevPowerSupply 349 }

-- Cisco Catalyst C4500X C4KX-PWR-750DC-R 750W DC Power Supply with Front to Back Cooling

cevPowerSupplyC4KXPWR750ACR  OBJECT IDENTIFIER
    ::= { cevPowerSupply 350 }

-- Cisco Catalyst C4500X C4KX-PWR-750AC-R 750W AC Power Supply with Front to Back Cooling

cevPowerSupplyNXAPac200WB  OBJECT IDENTIFIER
    ::= { cevPowerSupply 351 }

-- N2K/3K 200W AC Power, Reversed airflow (port side intake)

cevPowerSupplyNXAPac200W  OBJECT IDENTIFIER
    ::= { cevPowerSupply 352 }

-- N2K/3K 200W AC Power Supply, Std airflow (port side exhaust)

cevPowerSupplyISR4400Unknown  OBJECT IDENTIFIER
    ::= { cevPowerSupply 353 }

-- Cisco ISR 4400 Series Unknown Power Supply Module

cevPowerSupplyASR9000vGenericPm  OBJECT IDENTIFIER
    ::= { cevPowerSupply 354 }

-- ASR-9000v Generic Power Module

cevPowerSupplyNXAPac1100W  OBJECT IDENTIFIER
    ::= { cevPowerSupply 355 }

-- Nexus PSU module, 100-240VAC 1100W

cevPowerSupplyNXAPac1100WB  OBJECT IDENTIFIER
    ::= { cevPowerSupply 359 }

-- Nexus PSU module, 100-240VAC 1100W, Reversed airflow

cevPowerSupplyN3kPac400WB  OBJECT IDENTIFIER
    ::= { cevPowerSupply 360 }

-- Nexus 3548 series 400W AC Power Supply, Back to Front Airflow

cevPowerSupplyN3kPac400W  OBJECT IDENTIFIER
    ::= { cevPowerSupply 361 }

-- Nexus 3548 series 400W AC Power Supply, Front to Back Airflow

cevPowerSupplyNXAPAC500W  OBJECT IDENTIFIER
    ::= { cevPowerSupply 362 }

-- N3K-C3064TQ  Series 500W AC Power Supply, Front to Back Airflow

cevPowerSupplyNXAPAC500WB  OBJECT IDENTIFIER
    ::= { cevPowerSupply 363 }

-- N3K-C3064TQ  Series 500W AC Power Supply, Back to Front Airflow

cevPowerSupplyISR4400PS  OBJECT IDENTIFIER
    ::= { cevPowerSupply 364 }

-- Cisco ISR 4400 Series Generic Power Supply Module

cevPowerSupplyN55PDC1100W  OBJECT IDENTIFIER
    ::= { cevPowerSupply 365 }

-- Nexus 5500 1100W DC Power Supply

cevPowerSupplyASA5545PSInputSensor  OBJECT IDENTIFIER
    ::= { cevPowerSupply 366 }

-- Power Supply unit sensor in Adaptive Security Appliance 5545

cevPowerSupplyASA5555PSInputSensor  OBJECT IDENTIFIER
    ::= { cevPowerSupply 367 }

-- Power Supply unit sensor in Adaptive Security Appliance 5555

cevPowerSupplyASA5545K7PSInputSensor  OBJECT IDENTIFIER
    ::= { cevPowerSupply 368 }

-- Power Supply unit sensor in Adaptive Security Appliance 5545 with No Payload Encryption

cevPowerSupplyASA5555K7PSInputSensor  OBJECT IDENTIFIER
    ::= { cevPowerSupply 369 }

-- Power Supply unit sensor in Adaptive Security Appliance 5555 with No Payload Encryption

cevPowerSupplyCat2960XAC173W  OBJECT IDENTIFIER
    ::= { cevPowerSupply 370 }

-- 173 W SierraCool Power Supply for WS-C2960X-24PSK-L

cevPowerSupplyDS9710  OBJECT IDENTIFIER
    ::= { cevPowerSupply 374 }

-- Power Supply module for MDS 10-Slot Director Switch, DS9710

cevPowerSupplyDSC50I300AC  OBJECT IDENTIFIER
    ::= { cevPowerSupply 380 }

-- DS-C50I-300AC, Power Supply unit for MDS 9250i Intelligent Fabric Switch

cevPowerSupplyDSCAC973KW  OBJECT IDENTIFIER
    ::= { cevPowerSupply 381 }

-- DS-CAC97-3KW, AC Power Supply module for MDS 10-Slot Director Switch, DS9710

cevPowerSupplyDSCDC973KW  OBJECT IDENTIFIER
    ::= { cevPowerSupply 382 }

-- DS-CDC97-3KW, DC Power Supply module for MDS 10-Slot Director Switch, DS9710

cevPowerSupplyN77AC3KW  OBJECT IDENTIFIER
    ::= { cevPowerSupply 383 }

-- Nexus7700 AC 3000W  power supply

cevPowerSupplyN77DC3KW  OBJECT IDENTIFIER
    ::= { cevPowerSupply 384 }

-- Nexus7700 DC 3000W  power supply

cevPowerSupplyNXAPDC500W  OBJECT IDENTIFIER
    ::= { cevPowerSupply 399 }

-- Nexus Access Switches 500W DC PSU , Forward Air Flow (port-side exhaust)

cevPowerSupplyNXAPDC500WB  OBJECT IDENTIFIER
    ::= { cevPowerSupply 400 }

-- Nexus Access Switches 500W DC PSU , Reversed Air Flow (port-side intake)

cevPowerSupplyN9KAC3000W  OBJECT IDENTIFIER
    ::= { cevPowerSupply 404 }

-- N9K-PAC-3000W  AC 3KW powersupply for Nexus 9508

cevPowerSupplyN9KPac1200WB  OBJECT IDENTIFIER
    ::= { cevPowerSupply 405 }

-- TOR PSU, 1200W AC PSU, REVERSE (BACK TO FRONT) AIRFLOW

cevPowerSupplyN9KPac1200W  OBJECT IDENTIFIER
    ::= { cevPowerSupply 406 }

-- TOR PSU, 1200W AC PSU, NORMAL (FRONT TO BACK) AIRFLOW

cevPowerSupplyN9KPac650WB  OBJECT IDENTIFIER
    ::= { cevPowerSupply 407 }

-- TOR PSU, 650W AC PSU, REVERSE (BACK TO FRONT) AIRFLOW

cevPowerSupplyN9KPac650W  OBJECT IDENTIFIER
    ::= { cevPowerSupply 408 }

-- TOR PSU, 650W AC PSU, NORMAL (FRONT TO BACK) AIRFLOW

cevPowerSupply30WAC  OBJECT IDENTIFIER
    ::= { cevPowerSupply 416 }

-- Power Supply 30 Watt AC

cevPowerSupply60WAC  OBJECT IDENTIFIER
    ::= { cevPowerSupply 417 }

-- Power Supply 60 Watt AC

cevPowerSupply60WACV2  OBJECT IDENTIFIER
    ::= { cevPowerSupply 418 }

-- Power Supply 60 Watt AC

cevPowerSupply125WAC  OBJECT IDENTIFIER
    ::= { cevPowerSupply 419 }

-- POE power supply

cevPowerSupplyRT2241PWRAC  OBJECT IDENTIFIER
    ::= { cevPowerSupply 420 }

-- Router 2241 AC Power Supply

cevPowerSupplyRT3201PWRAC  OBJECT IDENTIFIER
    ::= { cevPowerSupply 421 }

-- Router 3201 AC Power Supply

cevPowerSupplyRT3211PWRAC  OBJECT IDENTIFIER
    ::= { cevPowerSupply 422 }

-- Router 3211 AC Power Supply

cevPowerSupplyRT3211PWRDC  OBJECT IDENTIFIER
    ::= { cevPowerSupply 423 }

-- Router 3211 DC Power Supply

cevPowerSupplyRT32PWRAC  OBJECT IDENTIFIER
    ::= { cevPowerSupply 424 }

-- Router 3200 AC Power Supply

cevPowerSupplyRT3211RPSADPTR  OBJECT IDENTIFIER
    ::= { cevPowerSupply 425 }

-- Router 3211 RPS Adapter for use with External RPS

cevPowerSupplyRT32RPSADPTR  OBJECT IDENTIFIER
    ::= { cevPowerSupply 426 }

-- Router 3200 RPS Adapter for use with External RPS

cevFan  OBJECT IDENTIFIER
    ::= { cevMIBObjects 7 }

cevFanC6260FanTray  OBJECT IDENTIFIER
    ::= { cevFan 3 }

-- Cisco 6260 Fan Tray

cevFanSinglePulse  OBJECT IDENTIFIER
    ::= { cevFan 4 }

-- Single Pulse Fan used in Cisco MGX series and other products.

cevFanDualPulse  OBJECT IDENTIFIER
    ::= { cevFan 5 }

-- Dual Pulse Fan used in Cisco MGX series and other products

cevFan12012FanTray3  OBJECT IDENTIFIER
    ::= { cevFan 6 }

-- Cisco 12012 Fan tray with 3 fans

cevFan12008FanTray6  OBJECT IDENTIFIER
    ::= { cevFan 7 }

-- Cisco 12008 Fan tray with 6 fans

cevFan12008FanTray4  OBJECT IDENTIFIER
    ::= { cevFan 8 }

-- Cisco 12008 Fan tray with 4 fans

cevFanC6160FanTray  OBJECT IDENTIFIER
    ::= { cevFan 9 }

-- Cisco 6160 Blower Module

cevFanC6100FanTray  OBJECT IDENTIFIER
    ::= { cevFan 11 }

-- Cisco 6100 Blower Module

cevFan12010FanTray3  OBJECT IDENTIFIER
    ::= { cevFan 13 }

-- Cisco 12010 Fan tray with 3 fans

cevFan12406FanTray3  OBJECT IDENTIFIER
    ::= { cevFan 14 }

-- Cisco 12406 Fan tray with 3 fans

cevFan12410FanTray3  OBJECT IDENTIFIER
    ::= { cevFan 15 }

-- Cisco 12410 Fan tray with 3 fans

cevFanONS15540FanTray8  OBJECT IDENTIFIER
    ::= { cevFan 16 }

-- Cisco ONS 15540 ESP fan tray module populated with 8 fans

cevFan12404FanTray7  OBJECT IDENTIFIER
    ::= { cevFan 17 }

-- Cisco 12404 Fan tray with 7 fans

cevFanBP7513MainFan  OBJECT IDENTIFIER
    ::= { cevFan 18 }

-- Cisco 7513 main blower

cevFanBP7513PS1Fan  OBJECT IDENTIFIER
    ::= { cevFan 19 }

-- Cisco 7513 PS1 Fan

cevFanBP7513PS2Fan  OBJECT IDENTIFIER
    ::= { cevFan 20 }

-- Cisco 7513 PS2 Fan

cevFan7505Fan  OBJECT IDENTIFIER
    ::= { cevFan 21 }

-- Cisco 7505 Fan

cevFan7507Fan  OBJECT IDENTIFIER
    ::= { cevFan 22 }

-- Cisco 7507 Fan

cevFanC7300PowerSupplyFan  OBJECT IDENTIFIER
    ::= { cevFan 23 }

-- Cisco 7300 platform Power Supply Fan

cevFanC7300FanModule  OBJECT IDENTIFIER
    ::= { cevFan 24 }

-- Cisco 7300 platform Fan

cevFanTrayC10008  OBJECT IDENTIFIER
    ::= { cevFan 25 }

-- Cisco  10008 Fan Tray

cevFanTrayC10005  OBJECT IDENTIFIER
    ::= { cevFan 26 }

-- Cisco  10005 Fan Tray

cevFanCat4kFanTray  OBJECT IDENTIFIER
    ::= { cevFan 27 }

-- Cisco Catalyst 4000 fan tray

cevFanCat4kPowerSupplyFan  OBJECT IDENTIFIER
    ::= { cevFan 28 }

-- Cisco Catalyst 4000 power supply fan

cevFanC6160ITempFanTray  OBJECT IDENTIFIER
    ::= { cevFan 29 }

-- Cisco 6160 ITemp Blower Module

cevFanONS15530FanTray6  OBJECT IDENTIFIER
    ::= { cevFan 30 }

-- Cisco ONS 15530 fan tray module with 6 fans

cevFan12016FanTray3  OBJECT IDENTIFIER
    ::= { cevFan 31 }

-- Cisco 12016 Fan tray with 3 fans

cevFanCat3750CFM26  OBJECT IDENTIFIER
    ::= { cevFan 34 }

-- Cisco Catalyst 3750 Fan, 26 CFM cool air flow.

cevFanDs6SlotFanTray  OBJECT IDENTIFIER
    ::= { cevFan 35 }

-- MDS 9506 Fan Tray(ProductID DS-6SLOT-FAN)

cevFanDs9SlotFanTray  OBJECT IDENTIFIER
    ::= { cevFan 36 }

-- MDS 9509 Fan Tray(ProductID DS-9SLOT-FAN)

cevFanDs13SlotFanTray  OBJECT IDENTIFIER
    ::= { cevFan 37 }

-- MDS 9513 Fan Tray(ProductID DS-13SLOT-FAN)

cevFanTrayUnknown  OBJECT IDENTIFIER
    ::= { cevFan 38 }

-- Unknown Fan Tray

cevFanDs2SlotFanTray  OBJECT IDENTIFIER
    ::= { cevFan 39 }

-- MDS 9216 Fan Tray(ProductID DS-2SLOT-FAN)

cevFanCat3710CFM26  OBJECT IDENTIFIER
    ::= { cevFan 40 }

-- Cisco Catalyst 3710 Fan, 26 CFM cool air flow

cevFanCat37xx12  OBJECT IDENTIFIER
    ::= { cevFan 41 }

-- Cisco 37xx12 Fan

cevFanWS9SlotFanTray  OBJECT IDENTIFIER
    ::= { cevFan 42 }

-- Catalyst 65509 Fan Tray

cevFanMod9FanTray  OBJECT IDENTIFIER
    ::= { cevFan 43 }

-- Cisco 7609 and Catalyst 6509-NEB-A Fan Tray

cevFanCat2970CFM26  OBJECT IDENTIFIER
    ::= { cevFan 44 }

-- Cisco Catalyst 2970 Fan, 26 CFM cool air flow

cevFanDs1RUFanTray  OBJECT IDENTIFIER
    ::= { cevFan 45 }

-- DS-1RU-FAN - MDS 1RU Fan Tray

cevFanFanMod3  OBJECT IDENTIFIER
    ::= { cevFan 46 }

-- Fan Module for  Catalyst 6503 / Cisco 7603 chassis

cevFanWSC6k6SlotFan  OBJECT IDENTIFIER
    ::= { cevFan 47 }

-- Catalyst 6000 Fan Tray for 6-Slot Systems

cevFanWSC6k6SlotFan2  OBJECT IDENTIFIER
    ::= { cevFan 48 }

-- High Speed Fan Tray for Catalyst 6506

cevFanWSC6k9SlotFan  OBJECT IDENTIFIER
    ::= { cevFan 49 }

-- Catalyst 6000 Fan Tray for 9-Slot Systems

cevFanWSC6k9SlotFan2  OBJECT IDENTIFIER
    ::= { cevFan 50 }

-- Catalyst 6509 High Speed Fan Tray

cevFanWSC6509NebFan  OBJECT IDENTIFIER
    ::= { cevFan 51 }

-- Catalyst 6509-NEB Fan Tray for 9-Vertical-Slot System

cevFanWSC6k13SlotFan  OBJECT IDENTIFIER
    ::= { cevFan 52 }

-- Fan Tray for 13-Slot C6K

cevFanWSC6k13SlotFan2  OBJECT IDENTIFIER
    ::= { cevFan 53 }

-- High Speed Fan Tray,for Catalyst 6513 / Cisco 7613

cevFanFanMod3HS  OBJECT IDENTIFIER
    ::= { cevFan 54 }

-- High Speed Fan Module for Catalyst 6503 / Cisco 7603 chassis

cevFanWSC6509NebFan2  OBJECT IDENTIFIER
    ::= { cevFan 55 }

-- Catalyst 6509-NEB  High Speed Fan Tray for 9-Vertical-Slot System

cevFanFanMod6  OBJECT IDENTIFIER
    ::= { cevFan 56 }

-- Fan Module for  Cisco 7606 chassis

cevFanFanMod6HS  OBJECT IDENTIFIER
    ::= { cevFan 57 }

-- High Speed Fan Tray  for Cisco 7606 chassis

cevFanCrs1Fan  OBJECT IDENTIFIER
    ::= { cevFan 58 }

-- Cisco CRS1 Fan Tray.

cevFanCat3560CFM26  OBJECT IDENTIFIER
    ::= { cevFan 59 }

-- Cisco Catalyst 3560 Fan, 26 CFM cool air flow

cevFanDs1RUFanTray9116  OBJECT IDENTIFIER
    ::= { cevFan 60 }

-- MDS 9116 Fan Tray

cevFanWSC6506eFanTray  OBJECT IDENTIFIER
    ::= { cevFan 61 }

-- Catalyst 6506 Enhanced Fan Tray

cevFanWSC6509eFanTray  OBJECT IDENTIFIER
    ::= { cevFan 62 }

-- Catalyst 6509 Enhanced Fan Tray

cevFanWSC6513eFanTray  OBJECT IDENTIFIER
    ::= { cevFan 63 }

-- Catalyst 6513 Enhanced Fan Tray

cevFanWSC6503eFanTray  OBJECT IDENTIFIER
    ::= { cevFan 64 }

-- Catalyst 6503 Enhanced Fan Tray

cevFanUmg9820FanTray  OBJECT IDENTIFIER
    ::= { cevFan 65 }

-- umg9820 product's Fan Tray

cevFanMod4HS  OBJECT IDENTIFIER
    ::= { cevFan 66 }

-- Fan module for cisco7604

cevFanC4kFCFanTray  OBJECT IDENTIFIER
    ::= { cevFan 67 }

-- Cisco Catalyst 4000 fixed chassis fan tray

cevFan12410EnhFanTray3  OBJECT IDENTIFIER
    ::= { cevFan 68 }

-- Cisco 12410 Enhanced Fan tray with 3 fans

cevFan12406EnhFanTray3  OBJECT IDENTIFIER
    ::= { cevFan 69 }

-- Cisco 12406 Enhanced Fan tray with 3 fans

cevFan12416EnhFanTray3  OBJECT IDENTIFIER
    ::= { cevFan 70 }

-- Cisco 12416 Enhanced Fan tray with 3 fans

cevFan12404FanTray6  OBJECT IDENTIFIER
    ::= { cevFan 71 }

-- Cisco 12404 Fan tray with 6 fans

cevFan12404EnhFanTray6  OBJECT IDENTIFIER
    ::= { cevFan 72 }

-- Cisco 12404 Enhanced Fan tray with 6 fans

cevFan9513FanTrayR  OBJECT IDENTIFIER
    ::= { cevFan 73 }

-- Cisco MDS 9513 Rear Fan Tray

cevFanCat2960CFM22  OBJECT IDENTIFIER
    ::= { cevFan 74 }

-- Cisco Catalyst 2960 Fan, 22 CFM cool air flow

cevFanCat2960CFM26  OBJECT IDENTIFIER
    ::= { cevFan 75 }

-- Cisco Catalyst 2960 Fan, 26 CFM cool air flow

cevFanTrayUbr10012  OBJECT IDENTIFIER
    ::= { cevFan 76 }

-- Fan Assembly Module For The UBR10012

cevFanC6524  OBJECT IDENTIFIER
    ::= { cevFan 77 }

-- Catalyst 6524 Spare FAN Tray

cevFanCatEx500CFM22  OBJECT IDENTIFIER
    ::= { cevFan 78 }

-- Cisco Catalyst Express 500 Fan, 22 CFM cool air flow

cevFanCatEx500CFM32  OBJECT IDENTIFIER
    ::= { cevFan 79 }

-- Cisco Catalyst Express 500 Fan, 32 CFM cool air flow

cevFanCat3750CFM35  OBJECT IDENTIFIER
    ::= { cevFan 80 }

-- Cisco Catalyst 3750 Fan, 35 CFM cool air flow

cevFanCFM15  OBJECT IDENTIFIER
    ::= { cevFan 81 }

-- Cisco 15 CFM cool air flow 12v DC fan.

cevFanCrs1FabricFanTray  OBJECT IDENTIFIER
    ::= { cevFan 82 }

-- Cisco CRS-1 Series Fabric Card Chassis Fan tray

cevModuleCrs116FanTray  OBJECT IDENTIFIER
    ::= { cevFan 83 }

-- Cisco CRS-1 Series Fan Tray for 16 slots LCC

cevModuleCrs18FanTray  OBJECT IDENTIFIER
    ::= { cevFan 84 }

-- Cisco CRS-1 Series Fan Tray for 8 slots LCC

cevModuleCrs14FanTray  OBJECT IDENTIFIER
    ::= { cevFan 85 }

-- Cisco CRS-1 Series Fan Tray for 4 slots LC

cevFanC3KBLWR60CFM  OBJECT IDENTIFIER
    ::= { cevFan 86 }

-- Catalyst 3K Fan, 60 CFM

cevFanMod6ShsFanTray  OBJECT IDENTIFIER
    ::= { cevFan 87 }

-- High Speed Fan Module for CISCO7606-S Chassis

cevFanMod9ShsFanTray  OBJECT IDENTIFIER
    ::= { cevFan 88 }

-- High Speed Fan Module for CISCO7609-S Chassis

cevFanMod9StFanTray  OBJECT IDENTIFIER
    ::= { cevFan 89 }

-- Turbo Fan Module for CISCO7609-S Chassis

cevFanBlwrRPS2300  OBJECT IDENTIFIER
    ::= { cevFan 90 }

-- Blower Assembly for RPS2300

cevFanACE4710K9CpuFan  OBJECT IDENTIFIER
    ::= { cevFan 91 }

-- Cisco ACE 4710 CPU Blower

cevFanACE4710K9DimmFan  OBJECT IDENTIFIER
    ::= { cevFan 92 }

-- Cisco ACE 4710 DIMM Blower

cevFanACE4710K9PciFan  OBJECT IDENTIFIER
    ::= { cevFan 93 }

-- Cisco ACE 4710 PCI Axial Fan

cevFanWSC6509veFan  OBJECT IDENTIFIER
    ::= { cevFan 94 }

-- FAN Tray for Catalyst 6500 enhanced 9-slot vertical chassis

cevFanMod3ShsFanTray  OBJECT IDENTIFIER
    ::= { cevFan 95 }

-- Variable High Speed Fan Module for CISCO7603-S Chassis

cevFanSce8000FanTray  OBJECT IDENTIFIER
    ::= { cevFan 96 }

-- Cisco SCE8000 Fan tray

cevFanN7Kc7010MainFanTray  OBJECT IDENTIFIER
    ::= { cevFan 97 }

-- main system fan for Nexus7000 10 slot N7K

cevFanN7KC7010FabricFanTray  OBJECT IDENTIFIER
    ::= { cevFan 98 }

-- fabric fan for Nexus7000 10 slot N7K

cevFanASR1002  OBJECT IDENTIFIER
    ::= { cevFan 99 }

-- Cisco ASR1002 Fan Module

cevFanASR1004  OBJECT IDENTIFIER
    ::= { cevFan 100 }

-- Cisco ASR1004 Fan Module

cevFanASR1006  OBJECT IDENTIFIER
    ::= { cevFan 101 }

-- Cisco ASR1006 Fan Module

cevFanCe520Cfm22  OBJECT IDENTIFIER
    ::= { cevFan 102 }

-- Cisco Catalyst Express 520  Fan, 32 CFM cool air flow

cevFanCe520Cfm32  OBJECT IDENTIFIER
    ::= { cevFan 103 }

-- Cisco Catalyst Express 520  Fan, 32 CFM cool air flow

cevFanN5kC5020Fan  OBJECT IDENTIFIER
    ::= { cevFan 104 }

-- Fan for Nexus 5020

cevFanCat2918Cfm22  OBJECT IDENTIFIER
    ::= { cevFan 105 }

-- Cisco Catalyst 2918 Fan, 22 CFM cool air flow

cevFanC3KFAN16CFM  OBJECT IDENTIFIER
    ::= { cevFan 106 }

-- Fan Module for Catalyst 3560E-12D and 3560E-12SD

cevFanPowerSupplyFan  OBJECT IDENTIFIER
    ::= { cevFan 107 }

-- Generic power supply fan

cevFanN7Kc7018FanTray  OBJECT IDENTIFIER
    ::= { cevFan 109 }

-- N7K-C7018-FAN fan for Nexus7000 18 slot N7K

cevFanCrs16lccFntrB  OBJECT IDENTIFIER
    ::= { cevFan 110 }

-- Cisco CRS-1 16 Slot System Reduced-Noise Fan Tray

cevFanASR14K4FanTray  OBJECT IDENTIFIER
    ::= { cevFan 111 }

-- Cisco ASR14000 Series Fan Tray for 4-Slot Chassis

cevFanASR14K8FanTray  OBJECT IDENTIFIER
    ::= { cevFan 112 }

-- Cisco ASR14000 Series Fan Tray for 8-Slot Chassis

cevFanN5kC5010Fan  OBJECT IDENTIFIER
    ::= { cevFan 113 }

-- Fan for Nexus 5010

cevFanASR9KFan  OBJECT IDENTIFIER
    ::= { cevFan 114 }

-- Cisco ASR9K Generic Fan is under Fan Tray and contains Fan Speed Sensor

cevFanASR9010  OBJECT IDENTIFIER
    ::= { cevFan 115 }

-- Cisco ASR-9010 Fan Tray Module

cevFanASR9006  OBJECT IDENTIFIER
    ::= { cevFan 116 }

-- Cisco ASR-9006 Fan Tray Module

cevFanASR14K4Fan  OBJECT IDENTIFIER
    ::= { cevFan 117 }

-- Cisco ASR14000 Series Fan for 4-Slot Fan Tray

cevFanASR14K8Fan  OBJECT IDENTIFIER
    ::= { cevFan 118 }

-- Cisco ASR14000 Series Fan for 8-Slot Fan Tray

cevFanCrs14Fan  OBJECT IDENTIFIER
    ::= { cevFan 119 }

-- Cisco CRS-1 Series Fan for 4-Slot Fan Tray

cevFanCrs18Fan  OBJECT IDENTIFIER
    ::= { cevFan 120 }

-- Cisco CRS-1 Series Fan for 8-Slot Fan Tray

cevFanCrs116Fan  OBJECT IDENTIFIER
    ::= { cevFan 121 }

-- Cisco CRS-1 Series Fan for 16-Slot Fan Tray

cevFanN2kC2148TFan  OBJECT IDENTIFIER
    ::= { cevFan 122 }

-- Nexus 2000 FEX 1GE Fan Module

cevContainerUCSN10S6100Fan1  OBJECT IDENTIFIER
    ::= { cevFan 124 }

-- 1RU Fabric Chassis Fan Module

cevFanCat2960CFM32  OBJECT IDENTIFIER
    ::= { cevFan 125 }

-- Cisco Catalyst 2960 Fan, 32 CFM cool air flow

cevFanContainerUCSN10Fan2  OBJECT IDENTIFIER
    ::= { cevFan 126 }

-- Fan module for UCS 6140XP Fabric Interconnect

cevFanN7Kc7009FanTray  OBJECT IDENTIFIER
    ::= { cevFan 129 }

-- N7K-C7009-FAN  Trinacria-fan-nexus9slot

cevFanMEFanTray  OBJECT IDENTIFIER
    ::= { cevFan 130 }

-- Metro Ethernet 3600X/3800X Fan Tray with 3 fans

cevFanMXE5600  OBJECT IDENTIFIER
    ::= { cevFan 131 }

-- Fan module for Cisco MXE 5600 platform

cevFanC2360Fan  OBJECT IDENTIFIER
    ::= { cevFan 132 }

-- Catalyst 2360 FRU Twin Fan Tray

cevFanASR1001FanTray  OBJECT IDENTIFIER
    ::= { cevFan 133 }

-- Fan Tray for asr1001 chassis

cevFanASR1000Fan  OBJECT IDENTIFIER
    ::= { cevFan 134 }

-- Fan for asr1000 platform

cevFanN5548PFan  OBJECT IDENTIFIER
    ::= { cevFan 135 }

-- Fan for Nexus 5548

cevFanCrs16FanTrB  OBJECT IDENTIFIER
    ::= { cevFan 139 }

-- CRS Series Fan Tray for CRS-16/S-B

cevFanCat2928Cfm22  OBJECT IDENTIFIER
    ::= { cevFan 140 }

-- Cisco Catalyst 2928 Fan, 22 CFM cool air flow

cevFanCat2928Cfm32  OBJECT IDENTIFIER
    ::= { cevFan 141 }

-- Cisco Catalyst 2928 Fan, 32 CFM cool air flow

cevFanBlwrXPS2200  OBJECT IDENTIFIER
    ::= { cevFan 142 }

-- Field-replaceable blower for XPS-2200

cevFanN5596UPFan  OBJECT IDENTIFIER
    ::= { cevFan 143 }

-- Fan for Nexus 5596

cevFanN2kC2248TBFan  OBJECT IDENTIFIER
    ::= { cevFan 144 }

-- N2K-C2248 Series FEX Fan Module+E125, Back to Front Airflow

cevFanN2kC2232TBFan  OBJECT IDENTIFIER
    ::= { cevFan 145 }

-- N2K-C2232 Series FEX Fan Module, Back to Front Airflow

cevFanN3kC3064Fan  OBJECT IDENTIFIER
    ::= { cevFan 148 }

-- N3K-C3016 and N3K-C3064 Fan Module, Front to Back Airflow, Spare

cevFanUCS6248UPFan  OBJECT IDENTIFIER
    ::= { cevFan 149 }

-- UCS 6248 Fan Module

cevFanUCS6296UPFan  OBJECT IDENTIFIER
    ::= { cevFan 150 }

-- UCS 6296 Fan Module

cevFanOe694  OBJECT IDENTIFIER
    ::= { cevFan 151 }

-- Cisco Oe694 Fan

cevFanOe594  OBJECT IDENTIFIER
    ::= { cevFan 152 }

-- Cisco Oe594 Fan

cevFanOe294  OBJECT IDENTIFIER
    ::= { cevFan 153 }

-- Cisco Oe294 Fan

cevFanOe7571  OBJECT IDENTIFIER
    ::= { cevFan 154 }

-- Cisco Oe7571 Fan

cevFanOe7541  OBJECT IDENTIFIER
    ::= { cevFan 155 }

-- Cisco Oe7541 Fan

cevFanOe8541  OBJECT IDENTIFIER
    ::= { cevFan 156 }

-- Cisco Oe8541 Fan

cevFanCrs16SBFan  OBJECT IDENTIFIER
    ::= { cevFan 157 }

-- Cisco CRS Series Fan for CRS-16/S-B Fan Tray

cevFanCrs16FabricFan  OBJECT IDENTIFIER
    ::= { cevFan 158 }

-- Cisco CRS Series Fan for Fabric Card Chassis Fan Tray

cevFanASA5555PSFan  OBJECT IDENTIFIER
    ::= { cevFan 160 }

-- Power Supply Fan in Adapative Security Appliance 5555

cevFanASA5555ChassisFan  OBJECT IDENTIFIER
    ::= { cevFan 167 }

-- Chassis Cooling Fan in Adapative Security Appliance 5555

cevFanN3kC3064FanB  OBJECT IDENTIFIER
    ::= { cevFan 173 }

-- N3K-C3016 and N3K-C3064 Fan Module, Back to Front Airflow, Spare

cevFanASR903FanTray  OBJECT IDENTIFIER
    ::= { cevFan 174 }

-- ASR 900 Chassis Series 3RU FAN Tray

cevFanASR900Fan  OBJECT IDENTIFIER
    ::= { cevFan 175 }

-- Fan for ASR 900 Series platform

cevFanASR5KFANTLW  OBJECT IDENTIFIER
    ::= { cevFan 176 }

-- ASR-5000 Fan Tray, Lower

cevFanASR5KFANTUP  OBJECT IDENTIFIER
    ::= { cevFan 177 }

-- ASR-5000 Fan Tray, Upper

cevFanASR55FANTF  OBJECT IDENTIFIER
    ::= { cevFan 178 }

-- ASR5500 Fan Tray, Front

cevFanASR55FANTR  OBJECT IDENTIFIER
    ::= { cevFan 179 }

-- ASR5500 Fan Tray, Rear

cevFanN7Kc7004FanTray  OBJECT IDENTIFIER
    ::= { cevFan 180 }

-- N7K-C7004-FAN  fan for nexus 4slot-chassis

cevFanN3kC3048Fan  OBJECT IDENTIFIER
    ::= { cevFan 181 }

-- N3K-C3048 Fan Module, Front to Back Airflow, Spare

cevFanN3kC3048FanB  OBJECT IDENTIFIER
    ::= { cevFan 182 }

-- N3K-C3048 Fan Module, Back to Front Airflow, Spare

cevFanASR9001  OBJECT IDENTIFIER
    ::= { cevFan 183 }

-- ASR-9001 Fan Tray

cevFanTrayISR4400  OBJECT IDENTIFIER
    ::= { cevFan 185 }

-- Cisco ISR 4400 Series Fan Tray

cevFanAsr9922Fan  OBJECT IDENTIFIER
    ::= { cevFan 187 }

-- ASR 9922 Fan Tray

cevFanAirstrikeCpuBlower  OBJECT IDENTIFIER
    ::= { cevFan 188 }

-- CISCO Airstrike CPU Blower

cevFanMod13SeFanTray  OBJECT IDENTIFIER
    ::= { cevFan 189 }

-- Enhanced Fan Module for CISCO7613-s Chassis

cevFanN6kC600496PQFanB  OBJECT IDENTIFIER
    ::= { cevFan 190 }

-- Nexus 6004 Fan Module with Back to Front Airflow

cevFanN6kC600496PQFanF  OBJECT IDENTIFIER
    ::= { cevFan 191 }

-- Nexus 6004 Fan Module with Front to Back Airflow

cevFanN3kC3548PFanB  OBJECT IDENTIFIER
    ::= { cevFan 192 }

-- Nexus 3548 Fan Module, Back to Front Airflow, 3+1 Spare

cevFanN3kC3548PFan  OBJECT IDENTIFIER
    ::= { cevFan 193 }

-- Nexus 3548 Fan Module, Front to Back Airflow, 3+1 Spare

cevFanA9K9912FAN  OBJECT IDENTIFIER
    ::= { cevFan 194 }

-- ASR 9912 Fan Tray

cevFanISR4400Fan  OBJECT IDENTIFIER
    ::= { cevFan 195 }

-- Cisco ISR 4400 Series Generic Fan

cevFanAsr9010FanV2  OBJECT IDENTIFIER
    ::= { cevFan 196 }

-- ASR-9010 Fan Tray Version 2

cevFanCat2960XCFM23  OBJECT IDENTIFIER
    ::= { cevFan 197 }

-- Cisco Catalyst 2960X Fan, 23 CFM cool air flow for non -Pwr SKUs

cevFanCat2960XCFM38  OBJECT IDENTIFIER
    ::= { cevFan 198 }

-- Cisco Catalyst 2960X Fan, 38 CFM cool air flow for Pwr SKUs

cevFanDSC9710  OBJECT IDENTIFIER
    ::= { cevFan 200 }

-- DS-C9710-FAN, Fan module for MDS 10-Slot Director Switch, DS9710

cevFanDSC50I  OBJECT IDENTIFIER
    ::= { cevFan 203 }

-- DS-C50I-FAN, Fan module for MDS 9250i Intelligent Fabric Switch

cevFanCrs18SBFan  OBJECT IDENTIFIER
    ::= { cevFan 205 }

-- Cisco CRS Series Fan for 8-Slot/S-B Fan Tray

cevFanCrs18FanTrayB  OBJECT IDENTIFIER
    ::= { cevFan 206 }

-- CRS-8 Enhanced chassis fan tray for CRS400G

cevFanN77c7718Fan  OBJECT IDENTIFIER
    ::= { cevFan 207 }

-- Fan for Nexus7700 18-slot chassis

cevFanN77c7710Fan  OBJECT IDENTIFIER
    ::= { cevFan 208 }

-- Fan for Nexus7700 10-slot chassis

cevFanN3KC3172TQFAN  OBJECT IDENTIFIER
    ::= { cevFan 213 }

-- N3K QuickIron2 Fan (Front to Back Airflow)

cevFanN3KC3172TQFANB  OBJECT IDENTIFIER
    ::= { cevFan 214 }

-- N3K QuickIron2 Fan (Back to Front Airflow)

cevFanN3KC3172PQFANB  OBJECT IDENTIFIER
    ::= { cevFan 215 }

-- N3K QuickZinc2 Fan (Back to Front Airflow)

cevFanN3KC3172PQFAN  OBJECT IDENTIFIER
    ::= { cevFan 216 }

-- N3K QuickZinc2 Fan (Front to Back Airflow)

cevFanN3KC3132FAN  OBJECT IDENTIFIER
    ::= { cevFan 217 }

-- N3K Neptune Fan (Front to Back Airflow)

cevFanN3KC3132FANB  OBJECT IDENTIFIER
    ::= { cevFan 218 }

-- N3K Neptune Fan (Back to Front Airflow)

cevFanDSC9706FAN  OBJECT IDENTIFIER
    ::= { cevFan 219 }

-- Fan for MDS-9706 6-slot Director Switch

cevFanN9Kc9508FanTray  OBJECT IDENTIFIER
    ::= { cevFan 222 }

-- N9K-C9508-FAN fan tray for Nexus9508 chassis

cevFanN6kC6002FanB  OBJECT IDENTIFIER
    ::= { cevFan 227 }

-- Nexus 6002 Fan Module with Back to Front Airflow

cevFanN6kC6002FanF  OBJECT IDENTIFIER
    ::= { cevFan 228 }

-- Nexus 6002 Fan Module with Front to Back Airflow

cevFanDSC48SFAN  OBJECT IDENTIFIER
    ::= { cevFan 229 }

-- Fan module for MDS 9148 16G Fabric Switch

cevSensor  OBJECT IDENTIFIER
    ::= { cevMIBObjects 8 }

cevSensorMGX8800Temp  OBJECT IDENTIFIER
    ::= { cevSensor 11 }

-- Cabinet Temperature sensor device in MGX8800 Universal Chassis

cevSensorMGX8800PSVoltage  OBJECT IDENTIFIER
    ::= { cevSensor 12 }

-- Power Supply Voltage Monitoring device in MGX8800 Universal Chassis

cevSensorMGX8800FanSpeed  OBJECT IDENTIFIER
    ::= { cevSensor 13 }

-- Sensor Device for monitoring fan speed (in RPMs) in MGX8800 Universal Chassis

cevSensorONS15540Temp  OBJECT IDENTIFIER
    ::= { cevSensor 14 }

-- Cisco ONS 15540 ESP Temperature Sensor

cevSensorONS15540Power  OBJECT IDENTIFIER
    ::= { cevSensor 15 }

-- Cisco ONS 15540 ESP Power Sensor

cevSensor7500ChassisInterface  OBJECT IDENTIFIER
    ::= { cevSensor 16 }

-- Cisco 7500 Chassis Interface Sensor

cevSensorC7300InletTempVoltage  OBJECT IDENTIFIER
    ::= { cevSensor 17 }

-- Cisco 7300 platform inlet temperature/voltage sensor device

cevSensorC7300OutletTempVoltage  OBJECT IDENTIFIER
    ::= { cevSensor 18 }

-- Cisco 7300 platform outlet temperature/voltage sensor device

cevSensorC7300HotspotTempVoltage  OBJECT IDENTIFIER
    ::= { cevSensor 19 }

-- Cisco 7300 platform hot spot temperature/voltage sensor device

cevSensorC7300NseDbTempVoltage  OBJECT IDENTIFIER
    ::= { cevSensor 20 }

-- Cisco 7300 platform temperature/voltage sensor device on the NSE Daughterboard

cevSensorC7300PSFanState  OBJECT IDENTIFIER
    ::= { cevSensor 21 }

-- Cisco 7300 platform power supply and fan state sensor device

cevSensorC10KInletTemp  OBJECT IDENTIFIER
    ::= { cevSensor 22 }

-- Cisco 10000 Inlet Temp Sensor

cevSensorC10000CoreTemp  OBJECT IDENTIFIER
    ::= { cevSensor 23 }

-- Cisco 10000 Core Temp Sensor

cevSensorCat4kTemp  OBJECT IDENTIFIER
    ::= { cevSensor 24 }

-- Cisco Catalyst 4000 temperature sensor

cevSensorONS15530Temp  OBJECT IDENTIFIER
    ::= { cevSensor 25 }

-- Cisco ONS 15530 Temperature Sensor

cevSensorONS15530Power  OBJECT IDENTIFIER
    ::= { cevSensor 26 }

-- Cisco ONS 15530 Power Sensor

cevSensorVxsmVoltage  OBJECT IDENTIFIER
    ::= { cevSensor 27 }

-- Voice switch service module with voltage sensor, 4 port OC3/STM-1 compliant

cevSensorVxsmTemp  OBJECT IDENTIFIER
    ::= { cevSensor 28 }

-- Voice switch service module with temperature sensor, 4 port OC3/STM-1 compliant

cevSensor15302701Temp  OBJECT IDENTIFIER
    ::= { cevSensor 29 }

-- Cisco 15-3027-01 Temperature Sensor

cevSensorUnknown  OBJECT IDENTIFIER
    ::= { cevSensor 30 }

-- Unknown sensor

cevSensorModuleDeviceTemp  OBJECT IDENTIFIER
    ::= { cevSensor 31 }

-- Generic module device temperature sensor

cevSensorClock  OBJECT IDENTIFIER
    ::= { cevSensor 32 }

-- Generic clock sensor

cevSensorVtt  OBJECT IDENTIFIER
    ::= { cevSensor 33 }

-- Generic VTT sensor

cevSensorModulePowerOutputFail  OBJECT IDENTIFIER
    ::= { cevSensor 34 }

-- Generic module power output fail sensor

cevSensorModuleOutletTemp  OBJECT IDENTIFIER
    ::= { cevSensor 35 }

-- Generic module outlet temperature sensor

cevSensorModuleInletTemp  OBJECT IDENTIFIER
    ::= { cevSensor 36 }

-- Generic module inlet temperature sensor

cevSensorFanTrayStatus  OBJECT IDENTIFIER
    ::= { cevSensor 37 }

-- Generic fan tray status sensor

cevSensorPSFan  OBJECT IDENTIFIER
    ::= { cevSensor 38 }

-- Generic power supply fan sensor

cevSensorPSOutput  OBJECT IDENTIFIER
    ::= { cevSensor 39 }

-- Generic power supply output sensor

cevSensorPSInput  OBJECT IDENTIFIER
    ::= { cevSensor 40 }

-- Generic power supply input sensor

cevSensorCrs1Voltage  OBJECT IDENTIFIER
    ::= { cevSensor 41 }

-- Cisco CRS1 voltage sensoro

cevSensorCrs1Temp  OBJECT IDENTIFIER
    ::= { cevSensor 42 }

-- Cisco CRS1 Temperature sensor

cevSensorCrs1Current  OBJECT IDENTIFIER
    ::= { cevSensor 43 }

-- Cisco CRS1 Current sensor

cevSensorCrs1FanSpeed  OBJECT IDENTIFIER
    ::= { cevSensor 44 }

-- Cisco CRS1 Fan Speed sensor

cevSensorModuleDeviceVoltage  OBJECT IDENTIFIER
    ::= { cevSensor 45 }

-- Generic Module Device Voltage Sensor

cevSensorTransceiverRxPwr  OBJECT IDENTIFIER
    ::= { cevSensor 46 }

-- Transceiver Rx Power sensor

cevSensorTransceiverTxPwr  OBJECT IDENTIFIER
    ::= { cevSensor 47 }

-- Transceiver Tx Power sensor

cevSensorTransceiverCurrent  OBJECT IDENTIFIER
    ::= { cevSensor 48 }

-- Transceiver Current sensor

cevSensorTransceiverVoltage  OBJECT IDENTIFIER
    ::= { cevSensor 49 }

-- Transceiver Voltage sensor

cevSensorTransceiverTemp  OBJECT IDENTIFIER
    ::= { cevSensor 50 }

-- Transceiver Temperature sensor

cevSensorModuleFanUpgradeRequired  OBJECT IDENTIFIER
    ::= { cevSensor 51 }

-- Module sensor to require fan upgrading (for Cat6k)

cevSensorModuleInsufficientCooling  OBJECT IDENTIFIER
    ::= { cevSensor 52 }

-- Module sensor for insufficient cooling (for Cat6k)

cevSensorPSFanIncompatible  OBJECT IDENTIFIER
    ::= { cevSensor 55 }

-- Power Supply Fan Incompatible Sensor(for Cat6k)

cevSensorACE4710K9CPUTemp  OBJECT IDENTIFIER
    ::= { cevSensor 56 }

-- Cisco ACE 4710 CPU Temperature Sensor

cevSensorACE4710K9AmbientTemp  OBJECT IDENTIFIER
    ::= { cevSensor 57 }

-- Cisco ACE 4710 Ambient Temperature Sensor

cevSensorCpuFanSpeed  OBJECT IDENTIFIER
    ::= { cevSensor 58 }

-- Cisco Generic CPU Fan Speed Sensor

cevSensorACE4710K9DimmFanSpeed  OBJECT IDENTIFIER
    ::= { cevSensor 59 }

-- Cisco ACE 4710 DIMM Blower Fan Sensor

cevSensorACE4710K9PciFanSpeed  OBJECT IDENTIFIER
    ::= { cevSensor 60 }

-- Cisco ACE 4710 PCI Axial Fan Sensor

cevSensorModuleDeviceCurrent  OBJECT IDENTIFIER
    ::= { cevSensor 61 }

-- Generic Sensor for monitoring the electric current

cevSensorCrs16dcPemB  OBJECT IDENTIFIER
    ::= { cevSensor 62 }

-- Cisco CRS-1 16 Slot System Reduced-Noise DC PEM

cevSensorExternalContact  OBJECT IDENTIFIER
    ::= { cevSensor 63 }

-- External contact that may be connected to various inputs

cevSensorFanSpeed  OBJECT IDENTIFIER
    ::= { cevSensor 64 }

-- Cisco Generic Fan Speed Sensor

cevSensorCrs1PwrVoltage  OBJECT IDENTIFIER
    ::= { cevSensor 65 }

-- Cisco CRS1 Powersupply voltage sensor

cevSensorCrs1Led  OBJECT IDENTIFIER
    ::= { cevSensor 66 }

-- Cisco CRS1 LED sensor

cevSensorMXE5600Temp  OBJECT IDENTIFIER
    ::= { cevSensor 67 }

-- Generic MXE 5600 platform Temperature Sensor

cevSensorMXE5600FanSpeed  OBJECT IDENTIFIER
    ::= { cevSensor 68 }

-- Generic MXE 5600 platform Fan Speed Sensor

cevSensorMXE5600Voltage  OBJECT IDENTIFIER
    ::= { cevSensor 69 }

-- Generic MXE 5600 platform Voltage Sensor

cevSensorMXE5600Current  OBJECT IDENTIFIER
    ::= { cevSensor 70 }

-- Generic MXE 5600 platform Current Sensor

cevSensorModuleDevicePower  OBJECT IDENTIFIER
    ::= { cevSensor 132 }

-- Generic Sensor for monitoring the Power Sensor

cevSensorModuleDeviceFanRotation  OBJECT IDENTIFIER
    ::= { cevSensor 133 }

-- Generic Sensor for monitoring the Fan Rotation Sensor

cevSensorModuleDevicePressure  OBJECT IDENTIFIER
    ::= { cevSensor 134 }

-- Generic Sensor for monitoring the Altitude Sensor

cevSensorASR5000CardTemp  OBJECT IDENTIFIER
    ::= { cevSensor 151 }

-- Temperature sensor on supported cards in ASR5000 chassis

cevSensorASR5000CardVoltage  OBJECT IDENTIFIER
    ::= { cevSensor 152 }

-- Voltage sensor on supported cards in ASR5000 chassis

cevSensorASR5000FanTemp  OBJECT IDENTIFIER
    ::= { cevSensor 153 }

-- Temperature sensor on fan tray in ASR5000 chassis

cevSensorASR5500CardTemp  OBJECT IDENTIFIER
    ::= { cevSensor 154 }

-- Temperature sensor on supported cards in ASR5500 chassis

cevSensorASR5500CardVoltage  OBJECT IDENTIFIER
    ::= { cevSensor 155 }

-- Voltage sensor on supported cards in ASR5500 chassis

cevSensorASR5500CardPower  OBJECT IDENTIFIER
    ::= { cevSensor 156 }

-- Power sensor on supported cards in ASR5500 chassis

cevSensorASR5500CardAirFlow  OBJECT IDENTIFIER
    ::= { cevSensor 157 }

-- Air flow sensor on supported cards in ASR5500 chassis

cevSensorASR5500CardBinary  OBJECT IDENTIFIER
    ::= { cevSensor 158 }

-- Binary sensor on supported cards in ASR5500 chassis

cevSensorASR5500CardPercentage  OBJECT IDENTIFIER
    ::= { cevSensor 159 }

-- Percentage sensor on supported cards in ASR5500 chassis

cevSensorASR5500CardCurrent  OBJECT IDENTIFIER
    ::= { cevSensor 160 }

-- Current sensor on supported cards in ASR5500 chassis

cevSensorASR5500FanTemp  OBJECT IDENTIFIER
    ::= { cevSensor 161 }

-- Temperature sensor on fan tray in ASR5500 chassis

cevModule  OBJECT IDENTIFIER
    ::= { cevMIBObjects 9 }

-- cevModule is subdivided into sections like
-- cevModuleC36xxType and cevModuleAS5200Type. These represent
-- cards used only on the c36xx and AS5200 platforms.
-- vHwic2as contains cards that can be used interchangeably
-- across more than one platform
--   
-- Acronyms used in the cevModule section:
-- Pa      Port adapter
-- Pm      Port module
-- Wic   Wan Interface Card
-- Isa   Integrated Service Adapter
-- Ism   Integrated Service Module

cevModuleUnknownCard  OBJECT IDENTIFIER
    ::= { cevModule 1 }

-- cevModuleCommonCards - cards and daughtercards common to more
-- than one platform

cevModuleCommonCards  OBJECT IDENTIFIER
    ::= { cevModule 2 }

cevWicSerial1t  OBJECT IDENTIFIER
    ::= { cevModuleCommonCards 1 }

cevWicST3420  OBJECT IDENTIFIER
    ::= { cevModuleCommonCards 5 }

cevWicST2186  OBJECT IDENTIFIER
    ::= { cevModuleCommonCards 6 }

cevWicU3420  OBJECT IDENTIFIER
    ::= { cevModuleCommonCards 7 }

cevWicU2091  OBJECT IDENTIFIER
    ::= { cevModuleCommonCards 8 }

cevWicU20912081  OBJECT IDENTIFIER
    ::= { cevModuleCommonCards 9 }

cevWicST2186Leased  OBJECT IDENTIFIER
    ::= { cevModuleCommonCards 10 }

cevVicFxs  OBJECT IDENTIFIER
    ::= { cevModuleCommonCards 11 }

cevVicFxo  OBJECT IDENTIFIER
    ::= { cevModuleCommonCards 12 }

cevVicEm  OBJECT IDENTIFIER
    ::= { cevModuleCommonCards 13 }

cevAimCompression  OBJECT IDENTIFIER
    ::= { cevModuleCommonCards 14 }

-- Compression Advanced Interface Module (AIM)

cevWvic1dsuT1  OBJECT IDENTIFIER
    ::= { cevModuleCommonCards 16 }

-- WAN Voice Interface Card with a single port T1 DSU for 1600, 1700, 2600, or 3600 series

cevWvic1dsuE1  OBJECT IDENTIFIER
    ::= { cevModuleCommonCards 17 }

-- WAN Voice Interface Card with a single port E1 DSU for 1600, 1700, 2600, or 3600 series

cevWvic2dsuT1  OBJECT IDENTIFIER
    ::= { cevModuleCommonCards 18 }

-- WAN Voice Interface Card with a dual port T1 DSU for 1600, 1700, 2600, or 3600 series

cevWvic2dsuE1  OBJECT IDENTIFIER
    ::= { cevModuleCommonCards 19 }

-- WAN Voice Interface Card with a dual port E1 DSU for 1600, 1700, 2600, or 3600 series

cevWvic2dsuT1Di  OBJECT IDENTIFIER
    ::= { cevModuleCommonCards 20 }

-- WAN Voice Interface Card with a dual port E1 DSU with Drop and Insert for 1600, 1700, 2600, or 3600 series

cevWvic2dsuE1Di  OBJECT IDENTIFIER
    ::= { cevModuleCommonCards 21 }

-- WAN Voice Interface Card with a dual port E1 DSU with Drop and Insert for 1600, 1700, 2600, or 3600 series

cevAimEncryption  OBJECT IDENTIFIER
    ::= { cevModuleCommonCards 22 }

-- Encryption Advanced Interface Module for the c2600, c3620, c3640, and c3660

cevPmNmToAim  OBJECT IDENTIFIER
    ::= { cevModuleCommonCards 23 }

-- Network Module to Advanced Interface Port Module for the 1600 and 3600 series

cevDfc8ce1  OBJECT IDENTIFIER
    ::= { cevModuleCommonCards 24 }

-- 8 Primary Rate Interface (PRI) Channelized E1 (ce1) Dial Feature Card used in AS5400 and AS5800 platforms

cevDfc8ct1  OBJECT IDENTIFIER
    ::= { cevModuleCommonCards 25 }

-- 8 Primary Rate Interface (PRI) Channelized T1 (ct1) Dial Feature Card used in AS5400 and AS5800 platforms

cevDfcCt3  OBJECT IDENTIFIER
    ::= { cevModuleCommonCards 26 }

-- Channelized T3 (ct3) Dial Feature Card used in AS5400 and AS5800 platforms

cevDfcNp108  OBJECT IDENTIFIER
    ::= { cevModuleCommonCards 27 }

-- Nextport (np) Modem Dial Feature Card consisting of 3 modem modules, each module has 36 modems, for a total of 108 modems per card; used in AS5400 and AS5800 platforms

cevWicSerial2as  OBJECT IDENTIFIER
    ::= { cevModuleCommonCards 29 }

-- Wan Interface Card with 2 low speed sync/async serial ports for 2600, 3600 series

cevWicCsuDsuFT1  OBJECT IDENTIFIER
    ::= { cevModuleCommonCards 30 }

-- Wan Interface Card with 1 Fractional T1 DSU/CSU port for 2600, 3600 series

cevIsaIpsecMppe  OBJECT IDENTIFIER
    ::= { cevModuleCommonCards 31 }

-- Integrated Service Port Adapter, used in the 7100 and 7200 series as a module, and in the 7500 series as a Port Adapter.  Hardware Accelerator for IPSEC Encryption and Compression, and MPPE encryption.  May not be used in slot 5 of the 7100.

cevWicDslsar20150  OBJECT IDENTIFIER
    ::= { cevModuleCommonCards 32 }

-- DSLSAR ADSL WIC (Wan Interface Card) used in 1720, 1750, 2600 and 3600 series. DSLSAR - SAR (Segmentation & Reassembly) of ATM cells and can be used with any DSL (Digital Subscriber Line). Uses ADSL (Asymmetric Digital Subscriber Line) as the physical layer.

cevDfc2ce1  OBJECT IDENTIFIER
    ::= { cevModuleCommonCards 35 }

-- 2 Primary Rate Interface (PRI) Channelized E1 (ce1) Dial Feature Card used in AS5350 platform

cevDfcNp60  OBJECT IDENTIFIER
    ::= { cevModuleCommonCards 37 }

-- Nextport (np) Dial Feature Card, supports a total of 60 universal ports per card

cevSpeNp6  OBJECT IDENTIFIER
    ::= { cevModuleCommonCards 43 }

-- NextPort(np) SPE(DSP), supports 6 universal ports per spe

cevWvic2dsuT1DIR  OBJECT IDENTIFIER
    ::= { cevModuleCommonCards 47 }

-- WAN Voice Interface Cards with a dual port T1 DSU with drop & insert and protection switching relay for MWR1900

cevWvic2dsuE1DIR  OBJECT IDENTIFIER
    ::= { cevModuleCommonCards 48 }

-- WAN Voice Interface Cards with a dual port E1 DSU with drop & insert and protection switching relay for MWR1900

cevVic4vpFxsDid  OBJECT IDENTIFIER
    ::= { cevModuleCommonCards 49 }

-- 4 port Voice Interface Card; Each port can function as Foreign Exchange Station(FXS) or Direct Inward Dialing (DID) Voice Port

cevVic4fxoUsM1  OBJECT IDENTIFIER
    ::= { cevModuleCommonCards 50 }

-- Four port Foreign Exchange Office Voice Interface Card for US/North America or M1 interface

cevVic4fxoM2M3  OBJECT IDENTIFIER
    ::= { cevModuleCommonCards 51 }

-- Four port Foreign Exchange Office Voice Interface Card for M2 or M3 interface (software selectable on a card basis)

cevVic4fxoCAMA  OBJECT IDENTIFIER
    ::= { cevModuleCommonCards 52 }

-- Four port Foreign Exchange Office Voice Interface Card for US/North America with CAMA (Centralized Automated Message Accounting) 911 signalling support (software selectable per port basis)

cevWicEthernet  OBJECT IDENTIFIER
    ::= { cevModuleCommonCards 55 }

-- WIC-1ENET card for 17xx platforms

cevCeSA6DC  OBJECT IDENTIFIER
    ::= { cevModuleCommonCards 56 }

-- 6 Slot Storage Array disk shelf for Content Engines. 6 disks. DC power

cevCeSA6AC  OBJECT IDENTIFIER
    ::= { cevModuleCommonCards 57 }

-- 6 Slot Storage Array disk shelf for Content Engines. 6 disks. AC power

cevCeSA12AC  OBJECT IDENTIFIER
    ::= { cevModuleCommonCards 58 }

-- 12 Slot Storage Array disk shelf for Content Engines. 12 disks AC power

cevC2610XM1Fe  OBJECT IDENTIFIER
    ::= { cevModuleCommonCards 59 }

-- Card with 1 integrated fast ethernet interface with SDRAM for Cisco 2610XM platform

cevC2611XM2Fe  OBJECT IDENTIFIER
    ::= { cevModuleCommonCards 60 }

-- Card with 2 integrated fast ethernet interfaces with SDRAM for Cisco 2611XM platform

cevC2620XM1Fe  OBJECT IDENTIFIER
    ::= { cevModuleCommonCards 61 }

-- Card with 1 integrated fast ethernet interface with SDRAM for Cisco 2620XM platform

cevC2621XM2Fe  OBJECT IDENTIFIER
    ::= { cevModuleCommonCards 62 }

-- Card with 2 integrated fast ethernet interfaces with SDRAM for Cisco 2621XM platform

cevC2650XM1Fe  OBJECT IDENTIFIER
    ::= { cevModuleCommonCards 63 }

-- Card with 1 integrated fast ethernet interface with SDRAM for Cisco 2650XM platform

cevC2651XM2Fe  OBJECT IDENTIFIER
    ::= { cevModuleCommonCards 64 }

-- Card with 2 integrated fast ethernet interfaces with SDRAM for Cisco 2651XM platform

cevVic8fxoUsM1  OBJECT IDENTIFIER
    ::= { cevModuleCommonCards 65 }

-- 8 Port FXO Voice Interface Module for US/North America or M1 interface

cevCeSA14  OBJECT IDENTIFIER
    ::= { cevModuleCommonCards 66 }

-- 14 Slot Storage Array disk shelf for Content Engines

cevWicDslsar20174Isdn  OBJECT IDENTIFIER
    ::= { cevModuleCommonCards 67 }

-- Single port ADSL Wan Interface Card to support ADSL over ISDN and dying gasp, to be used on c1700, c2600 and c3700 routers

cevWicDslsar20174Pots  OBJECT IDENTIFIER
    ::= { cevModuleCommonCards 68 }

-- Single port ADSL Wan Interface Card to support ADSL over POTS and dying gasp, to be used on c1700, c2600 and c3700 routers

cevSpaIpSec2G  OBJECT IDENTIFIER
    ::= { cevModuleCommonCards 69 }

-- IPSec Shared Port Adapter with 2 Gbps DES/3DES/AES (SPA-IPSEC-2G)

cevNmSe  OBJECT IDENTIFIER
    ::= { cevModuleCommonCards 70 }

-- service engine network module

cevAimSe  OBJECT IDENTIFIER
    ::= { cevModuleCommonCards 71 }

-- service engine Advanced Interface Module

cevWicSe  OBJECT IDENTIFIER
    ::= { cevModuleCommonCards 72 }

-- service engine WIC

cevCeDs2100  OBJECT IDENTIFIER
    ::= { cevModuleCommonCards 73 }

-- Disk System 2100 for Content Engine.

cevDfc16ce1  OBJECT IDENTIFIER
    ::= { cevModuleCommonCards 74 }

-- 16 Primary Rate Interface (PRI) Channelized E1 (ce1) Dial Feature Card used in AS5400 and AS5800 platforms

cevDfc16ct1  OBJECT IDENTIFIER
    ::= { cevModuleCommonCards 75 }

-- 16 Primary Rate Interface (PRI) Channelized T1 (ct1) Dial Feature Card used in AS5400 and AS5800 platforms

cevSpa2pOc3Atm  OBJECT IDENTIFIER
    ::= { cevModuleCommonCards 76 }

-- 2-port OC3c/STM1c ATM Shared Port Adapter (SPA-2XOC3-ATM)

cevSpa4pOc3Atm  OBJECT IDENTIFIER
    ::= { cevModuleCommonCards 77 }

-- 4-port OC3c/STM1c ATM Shared Port Adapter (SPA-4XOC3-ATM)

cevSpa1pOc12Atm  OBJECT IDENTIFIER
    ::= { cevModuleCommonCards 78 }

-- 1-port OC12c/STM4c ATM Shared Port Adapter (SPA-1XOC12-ATM)

cevSpa1pOc48Atm  OBJECT IDENTIFIER
    ::= { cevModuleCommonCards 80 }

-- 1-port OC48/STM16 ATM Shared Port Adapter (SPA-1XOC48-ATM)

cevSpa2pOc3Pos  OBJECT IDENTIFIER
    ::= { cevModuleCommonCards 83 }

-- 2-port OC3c/STM1c POS Shared Port Adapter (SPA-2XOC3-POS)

cevSpa4pOc3Pos  OBJECT IDENTIFIER
    ::= { cevModuleCommonCards 84 }

-- 4-port OC3c/STM1c POS Shared Port Adapter (SPA-4XOC3-POS)

cevSpa1pOc12Pos  OBJECT IDENTIFIER
    ::= { cevModuleCommonCards 85 }

-- 1-port OC12c/STM4c POS Shared Port Adapter (SPA-1XOC12-POS)

cevSpa2pOc12Pos  OBJECT IDENTIFIER
    ::= { cevModuleCommonCards 86 }

-- 2-port OC12c/STM4c Multirate POS Shared Port Adapter (SPA-2XOC12-POS)

cevSpa8pOc12Pos  OBJECT IDENTIFIER
    ::= { cevModuleCommonCards 87 }

-- 8-port OC12c/STM4c Multirate POS Shared Port Adapter (SPA-8XOC12-POS)

cevSpa4pFe7304  OBJECT IDENTIFIER
    ::= { cevModuleCommonCards 88 }

-- 4-port 10/100 Ethernet Shared Port Adapter (SPA-4FE-7304)

cevSpa2pGe7304  OBJECT IDENTIFIER
    ::= { cevModuleCommonCards 89 }

-- 2 port 10/100/1000 Ethernet Shared Port Adapter (SPA-2GE-7304)

cevWicEswitch4  OBJECT IDENTIFIER
    ::= { cevModuleCommonCards 90 }

-- 4 Ports 10BaseT/100BaseTX Ethernet Switch card

cevWicBri3086u  OBJECT IDENTIFIER
    ::= { cevModuleCommonCards 91 }

-- BRI WIC U 3086

cevSpa1pOc192PosRprXfp  OBJECT IDENTIFIER
    ::= { cevModuleCommonCards 92 }

-- 1-port OC192c/STM64c POS/RPR XFP Optics Shared Port Adapter (SPA-OC192POS-XFP)

cevSpa1pOc192PosRprSmLr  OBJECT IDENTIFIER
    ::= { cevModuleCommonCards 94 }

-- 1-port OC192c/STM64c POS/RPR SMLR Optics Shared Port Adapter (SPA-OC192POS-LR)

cevSpa1pOc192PosRprVsr  OBJECT IDENTIFIER
    ::= { cevModuleCommonCards 95 }

-- 1-port OC192c/STM64c POS/RPR VSR Optics Shared Port Adapter (SPA-OC192POS-VSR)

cevSpa2pT3E3Serial  OBJECT IDENTIFIER
    ::= { cevModuleCommonCards 96 }

-- 2-port T3/E3 Serial Shared Port Adapter (SPA-2XT3/E3)

cevSpa4pT3E3Serial  OBJECT IDENTIFIER
    ::= { cevModuleCommonCards 97 }

-- 4-port T3/E3 Serial Shared Port Adapter (SPA-4XT3/E3)

cevSpa8pCT1E1  OBJECT IDENTIFIER
    ::= { cevModuleCommonCards 98 }

-- 8-port Channelized T1/E1 to DS0 Shared Port Adapter (SPA-8XCHT1/E1)

cevSpa2pCT3  OBJECT IDENTIFIER
    ::= { cevModuleCommonCards 99 }

-- 2-port Channelized T3 to DS0 Shared Port Adapter (SPA-2XCT3/DS0)

cevSpa4pCT3  OBJECT IDENTIFIER
    ::= { cevModuleCommonCards 100 }

-- 4-port Channelized T3 to DS0 Shared Port Adapter (SPA-4XCT3/DS0)

cevNmAONS  OBJECT IDENTIFIER
    ::= { cevModuleCommonCards 101 }

-- Application-Oriented Networking System (AONS) Network Module

cevHwic4fe  OBJECT IDENTIFIER
    ::= { cevModuleCommonCards 102 }

-- HWIC ESW 4 Port Fast Ethernet Cards

cevHwic9fes  OBJECT IDENTIFIER
    ::= { cevModuleCommonCards 103 }

-- HWIC 9 Port Fast Ethernet Switch Cards

cevHwic4fes  OBJECT IDENTIFIER
    ::= { cevModuleCommonCards 104 }

-- HWIC 4 Port Fast Ethernet Switch Cards

cevHwic4ilp  OBJECT IDENTIFIER
    ::= { cevModuleCommonCards 105 }

-- 4-Port HWIC-ESW Inline Power Daughter Card

cevHwic9ilp  OBJECT IDENTIFIER
    ::= { cevModuleCommonCards 106 }

-- 9-Port HWIC-ESW Inline Power Daughter Card

cevSpa10pGe  OBJECT IDENTIFIER
    ::= { cevModuleCommonCards 107 }

-- 10-port Gigabit Ethernet Shared Port Adapter (SPA-10X1GE)

cevSpa1p10GeXfp  OBJECT IDENTIFIER
    ::= { cevModuleCommonCards 108 }

-- 1-port 10 Gigabit Ethernet Shared Port Adapter XFP based (SPA-1XTENGE-XFP)

cevSpa5pGe  OBJECT IDENTIFIER
    ::= { cevModuleCommonCards 109 }

-- 5-port Gigabit Ethernet Shared Port Adapter (SPA-5X1GE)
-- Assignment Cancelled. Reuse the OID  cevSpa4pOc48PosRprHH   OBJECT IDENTIFIER ::= { cevModuleCommonCards 113 }       4-port OC48/STM16 POS/RPR Shared Port Adapter
-- Assignment Cancelled. Reuse the OID  cevSpa8pOc3Oc12Pos   OBJECT IDENTIFIER ::= { cevModuleCommonCards 114 }       8-port OC3/STM1 OC12/STM4 POS Shared Port Adapter

cevSpa2pGe  OBJECT IDENTIFIER
    ::= { cevModuleCommonCards 115 }

-- 2-port Gigabit Ethernet Shared Port Adapter (SPA-2X1GE)

cevCompactFlash64MB  OBJECT IDENTIFIER
    ::= { cevModuleCommonCards 116 }

-- 64MB compact flash disk

cevCompactFlash128MB  OBJECT IDENTIFIER
    ::= { cevModuleCommonCards 117 }

-- 128MB compact flash disk

cevCompactFlash256MB  OBJECT IDENTIFIER
    ::= { cevModuleCommonCards 118 }

-- 256MB compact flash disk

cevCompactFlash512MB  OBJECT IDENTIFIER
    ::= { cevModuleCommonCards 119 }

-- 512MB compact flash disk

cevCompactFlash  OBJECT IDENTIFIER
    ::= { cevModuleCommonCards 120 }

-- Compact Flash

cevSpa1pChOc3Stm1  OBJECT IDENTIFIER
    ::= { cevModuleCommonCards 121 }

-- 1-port Channelized STM1/OC3 to DS0 Shared Port Adapter (SPA-1XCHSTM1/OC3)

cevFlashCard48MB  OBJECT IDENTIFIER
    ::= { cevModuleCommonCards 122 }

-- 48MB  flash disk

cevFlashCard64MB  OBJECT IDENTIFIER
    ::= { cevModuleCommonCards 123 }

-- 64MB  flash disk

cevFlashCard128MB  OBJECT IDENTIFIER
    ::= { cevModuleCommonCards 124 }

-- 128MB flash disk

cevFlashCard256MB  OBJECT IDENTIFIER
    ::= { cevModuleCommonCards 125 }

-- 256MB flash disk

cevFlashCard512MB  OBJECT IDENTIFIER
    ::= { cevModuleCommonCards 126 }

-- 512MB flash disk

cevFlashCard  OBJECT IDENTIFIER
    ::= { cevModuleCommonCards 127 }

-- flash disk

cevHwicdot11abg  OBJECT IDENTIFIER
    ::= { cevModuleCommonCards 128 }

-- 802.11 a/b/g Access Point

cevHwicdot11bg  OBJECT IDENTIFIER
    ::= { cevModuleCommonCards 129 }

-- 802.11 b/g Access Point

cevAimVpnBp  OBJECT IDENTIFIER
    ::= { cevModuleCommonCards 130 }

-- VPN Encryption Advanced Interface Module - Base Performance

cevAimVpnEp  OBJECT IDENTIFIER
    ::= { cevModuleCommonCards 131 }

-- VPN Encryption Advanced Interface Module - Enhanced Performance

cevNmVpnMp  OBJECT IDENTIFIER
    ::= { cevModuleCommonCards 132 }

-- VPN Encryption Network Module - Mid Performance

cevAimVpnHp  OBJECT IDENTIFIER
    ::= { cevModuleCommonCards 133 }

-- VPN Encryption Advanced Interface Module - High

cevAimVpnBp2  OBJECT IDENTIFIER
    ::= { cevModuleCommonCards 134 }

-- VPN Encryption Advanced Interface Module - Base Performance (version 2)

cevAimVpnEp2  OBJECT IDENTIFIER
    ::= { cevModuleCommonCards 135 }

-- VPN Encryption Advanced Interface Module - Enhanced Performance (version 2)

cevAimVpnHp2  OBJECT IDENTIFIER
    ::= { cevModuleCommonCards 136 }

-- VPN Encryption Advanced Interface Module - High Performance (version 2)

cevAimVpnBp2Plus  OBJECT IDENTIFIER
    ::= { cevModuleCommonCards 137 }

-- VPN Encryption Advanced Interface Module - Base Performance (version 2 Plus)

cevAimVpnEp2Plus  OBJECT IDENTIFIER
    ::= { cevModuleCommonCards 138 }

-- VPN Encryption Advanced Interface Module - Enhanced Performance (version 2 Plus)

cevAimVpnHp2Plus  OBJECT IDENTIFIER
    ::= { cevModuleCommonCards 139 }

-- VPN Encryption Advanced Interface Module - High Performance (version 2 Plus)

cevHwicAdslBriPots  OBJECT IDENTIFIER
    ::= { cevModuleCommonCards 140 }

-- ADSL over POTS and BRI S/T

cevHwicAdslBriIsdn  OBJECT IDENTIFIER
    ::= { cevModuleCommonCards 141 }

-- ADSL over ISDN and BRI S/T

cevHwicAdslIsdn  OBJECT IDENTIFIER
    ::= { cevModuleCommonCards 142 }

-- ADSL over ISDN

cevHwicAdslPots  OBJECT IDENTIFIER
    ::= { cevModuleCommonCards 143 }

-- ADSL over POTS

cevSpa2pOc48PosRprHH  OBJECT IDENTIFIER
    ::= { cevModuleCommonCards 144 }

-- 2-Port OC48c/STM16c POS/RPR Shared Port Adapter (SPA-2XOC48POS/RPR)

cevNMCueEc  OBJECT IDENTIFIER
    ::= { cevModuleCommonCards 146 }

-- Service Engine Network Module with 512MB RAM

cevC180xdot11abg  OBJECT IDENTIFIER
    ::= { cevModuleCommonCards 147 }

-- 802.11 a/b/g Access Point for c180x/c181x

cevC180xdot11bg  OBJECT IDENTIFIER
    ::= { cevModuleCommonCards 148 }

-- 802.11 b/g Access Point for c180x/c181x

cevC180x8ilp  OBJECT IDENTIFIER
    ::= { cevModuleCommonCards 149 }

-- 8-Port ESW Inline Power Daughter Card for c180x/c181x

cevDfcDl108  OBJECT IDENTIFIER
    ::= { cevModuleCommonCards 150 }

-- These cards are similar to DFC-NP108 and DFC-NP60 used on AS5400 platforms, but they are capable of only dial calls.

cevDfcDl60  OBJECT IDENTIFIER
    ::= { cevModuleCommonCards 151 }

-- These cards are similar to DFC-NP108 and DFC-NP60 used on AS5400 platforms, but they are capable of only dial calls.

cevNmWlanController  OBJECT IDENTIFIER
    ::= { cevModuleCommonCards 152 }

-- Wireless LAN controller Network Module

cevWicCsuDsuFT1v2  OBJECT IDENTIFIER
    ::= { cevModuleCommonCards 153 }

-- Wan Interface Card with 1 Fractional T1 CSU/DSU port, version 2

cevSpa8xfeTx  OBJECT IDENTIFIER
    ::= { cevModuleCommonCards 154 }

-- 8-Port Fast Ethernet Shared Port Adapter (SPA-8XFE-TX)

cevNMIntegratedServiceEngine  OBJECT IDENTIFIER
    ::= { cevModuleCommonCards 155 }

-- Integrated Service Engine for Modular and Integrated Services Routers

cevNmWaEngine  OBJECT IDENTIFIER
    ::= { cevModuleCommonCards 156 }

-- A network module sittig on the 26xx/37xx/28xx/38xx platforms and running wan application services on linux. The module will be called as wan-application-engine in CLI.

cevSpa2pGeV2  OBJECT IDENTIFIER
    ::= { cevModuleCommonCards 157 }

-- 2-port Gigabit Ethernet Shared Port Adapter V2 (SPA-2X1GE-V2)

cevSpa5pGeV2  OBJECT IDENTIFIER
    ::= { cevModuleCommonCards 158 }

-- 5-port Gigabit Ethernet Shared Port Adapter V2 (SPA-5X1GE-V2)

cevSpa8pGeV2  OBJECT IDENTIFIER
    ::= { cevModuleCommonCards 159 }

-- 8-port Gigabit Ethernet Shared Port Adapter V2 (SPA-8X1GE-V2)

cevSpa10pGeV2  OBJECT IDENTIFIER
    ::= { cevModuleCommonCards 160 }

-- 10-port Gigabit Ethernet Shared Port Adapter V2 (SPA-10X1GE-V2)

cevSpa1p10GeXfpV2  OBJECT IDENTIFIER
    ::= { cevModuleCommonCards 161 }

-- 1-port 10 Gigabit Ethernet Shared Port Adapter V2 (SPA-1X10GE-L-V2)

cevSpa8xfeTxV2  OBJECT IDENTIFIER
    ::= { cevModuleCommonCards 162 }

-- 8-port Fast Ethernet Shared Port Adapter V2 (SPA-8X1FE-TX-V2)

cevModuleCrs14OC192IRPlim  OBJECT IDENTIFIER
    ::= { cevModuleCommonCards 163 }

-- Cisco CRS-1 Series 4xOC192/STM64 POS/DPT Interface Module/IR

cevSpa8xGe  OBJECT IDENTIFIER
    ::= { cevModuleCommonCards 164 }

-- 8-Port Gigabit Ethernet Shared Port Adapter (SPA-8X1GE)

cevSpa8xoc3Pos  OBJECT IDENTIFIER
    ::= { cevModuleCommonCards 166 }

-- 8-port OC3c/STM1c POS Shared Port Adapter (SPA-8XOC3-POS)

cevSpa4xoc12Pos  OBJECT IDENTIFIER
    ::= { cevModuleCommonCards 167 }

-- 4-port OC12c/STM4c Multirate POS Shared Port Adapter (SPA-4XOC12-POS)

cevWic1ShdslV3  OBJECT IDENTIFIER
    ::= { cevModuleCommonCards 168 }

-- WAN Interface Card -ATM (With multi line G.SHDSL module)

cevUsbFlash  OBJECT IDENTIFIER
    ::= { cevModuleCommonCards 169 }

-- Universal Serial Bus (USB) Flash Disk.

cevUsbToken  OBJECT IDENTIFIER
    ::= { cevModuleCommonCards 170 }

-- Universal Serial Bus (USB) Token Disk.

cevUsbHub  OBJECT IDENTIFIER
    ::= { cevModuleCommonCards 171 }

-- Universal Serial Bus (USB) Hub

cevVEncM  OBJECT IDENTIFIER
    ::= { cevModuleCommonCards 172 }

-- Video Encoder Module for Modular and Integrated Services Routers

cevUsbDevice  OBJECT IDENTIFIER
    ::= { cevModuleCommonCards 173 }

-- Generic Universal Serial Bus (USB) device

cevSpa1pOc48PosSfp  OBJECT IDENTIFIER
    ::= { cevModuleCommonCards 174 }

-- 1-port OC48c/STM16c POS/RPR SFP Optics Shared Port Adapter (SPA-1XOC48POS/RPR)

cevSpa4pOc48PosSfp  OBJECT IDENTIFIER
    ::= { cevModuleCommonCards 175 }

-- 4-port OC48c/STM16c POS/RPR SFP Optics Shared Port Adapter (SPA-4XOC48POS/RPR)

cevIpRanOpt4P  OBJECT IDENTIFIER
    ::= { cevModuleCommonCards 176 }

-- IP-RAN Optimization with four processors

cevAimIps1  OBJECT IDENTIFIER
    ::= { cevModuleCommonCards 177 }

-- Intrusion Detection Module for Access Routers 18xx

cevAimIps2  OBJECT IDENTIFIER
    ::= { cevModuleCommonCards 178 }

-- Intrusion Detection Module for Access Routers 28xx

cevNmCips  OBJECT IDENTIFIER
    ::= { cevModuleCommonCards 180 }

-- Intrusion Detection Module for Access Routers in NM form factor for 18xx, 28xx and 38xx family branch routers

cevHwic1fe  OBJECT IDENTIFIER
    ::= { cevModuleCommonCards 181 }

-- HWIC-1FE is a 1-port FE on a HWIC interface

cevHwic2fe  OBJECT IDENTIFIER
    ::= { cevModuleCommonCards 182 }

-- HWIC-2FE is a 2-port FE on a HWIC interface

cevHwicBriU82912  OBJECT IDENTIFIER
    ::= { cevModuleCommonCards 183 }

-- HWIC-1B-U is a BRI U interface module that provides a single Basic Rate ISDN U WAN interface

cevHwicBri4bST  OBJECT IDENTIFIER
    ::= { cevModuleCommonCards 184 }

-- HWIC-4B-S/T is a 4 port BRI S/T data only HWIC to replace the NM-4B-S/T and NM-8B-S/T modules

cevModuleCrs1RPB  OBJECT IDENTIFIER
    ::= { cevModuleCommonCards 185 }

-- Cisco CRS-1 Series 16 Slots Route Processor revision B

cevModuleCrs1FccSCGe  OBJECT IDENTIFIER
    ::= { cevModuleCommonCards 186 }

-- Cisco CRS-1 Series FCC Shelf Controller and GE Switch

cevModuleCrs1SPAInfCard  OBJECT IDENTIFIER
    ::= { cevModuleCommonCards 187 }

-- Cisco Carrier Routing System SPA Interface Processor Card

cevModule4OC192DptIr  OBJECT IDENTIFIER
    ::= { cevModuleCommonCards 188 }

-- Cisco CRS-1 4xOC-192/STM-64 DPT Interface Module/IR

cevModuleCrs116mFabricCard  OBJECT IDENTIFIER
    ::= { cevModuleCommonCards 189 }

-- Cisco CRS-1 Series 16 Slots Fabric Card / Multi

cevHwicAdslPotsAnnexM  OBJECT IDENTIFIER
    ::= { cevModuleCommonCards 190 }

-- ADSL Annex M over POTS

cevSpa4pOc3PosV2  OBJECT IDENTIFIER
    ::= { cevModuleCommonCards 191 }

-- 4-port OC-3c/STM1c POS Shared Port Adapter (SPA-4XOC3-POS-V2)

cevCVRX2SFP  OBJECT IDENTIFIER
    ::= { cevModuleCommonCards 192 }

-- 2-port SFP port module in X2 form factor

cevSpaIPSEC2g2  OBJECT IDENTIFIER
    ::= { cevModuleCommonCards 193 }

-- IPSec Shared Port Adapter with 2 Gbps DES/3DES/AES (SPA-IPSEC-2G-2)

cevSpa8pCt1e1CemAtm  OBJECT IDENTIFIER
    ::= { cevModuleCommonCards 194 }

-- 8-port Channelized T1/E1 ATM & Circuit Emulation Shared Port Adapter (SPA-8CHT1-CE-ATM)

cevSpa24pCt1e1CemAtm  OBJECT IDENTIFIER
    ::= { cevModuleCommonCards 195 }

-- 24-port Channelized T1/E1 ATM & Circuit Emulation Shared Port Adapter (SPA-24CHT1-CE-ATM)

cevSpa2pCt3e3CemAtm  OBJECT IDENTIFIER
    ::= { cevModuleCommonCards 196 }

-- 2-port Channelized T3/E3 ATM & Circuit Emulation Shared Port Adapter (SPA-2CHT3-CE-ATM)

cevSpa1pChoc3CemAtm  OBJECT IDENTIFIER
    ::= { cevModuleCommonCards 197 }

-- 1-port Channelized OC3/STM-1 ATM & Circuit Emulation Shared Port Adapter (SPA-1CHOC3-CE-ATM)

cevSpa1x10geWlV2  OBJECT IDENTIFIER
    ::= { cevModuleCommonCards 198 }

-- 1-port 10 Gigabit Ethernet Wanphy Shared Port Adapter V2

cevSpa1x10geDwdmV2  OBJECT IDENTIFIER
    ::= { cevModuleCommonCards 199 }

-- 1-port 10 Gigabit Ethernet DWDM Shared Port Adapter V2

cevSpa1pChoc48Ds3  OBJECT IDENTIFIER
    ::= { cevModuleCommonCards 200 }

-- 1 port channelized OC48 to DS3 Shared Port Adapter (SPA-1XCHOC48/DS3)

cevSpa1pChoc12Ds0  OBJECT IDENTIFIER
    ::= { cevModuleCommonCards 201 }

-- 1 port channelized OC12 to DS0 Shared Port Adapter (SPA-1XCHOC12/DS0)

cevAimAtm8  OBJECT IDENTIFIER
    ::= { cevModuleCommonCards 202 }

-- Advanced integration module for the MWR-1951-DC supporting the capacity to allow 8 Inverse Mux over ATM (IMA) groups

cevSpa4xtSerial  OBJECT IDENTIFIER
    ::= { cevModuleCommonCards 203 }

-- 4-port 12in1 Serial Shared Port Adapter (SPA-4XT-SERIAL)

cevSpa1xOC3AtmV2  OBJECT IDENTIFIER
    ::= { cevModuleCommonCards 204 }

-- 1-port OC3c SFP Optics ATM Shared Port Adapter

cevSpa2xOC3AtmV2  OBJECT IDENTIFIER
    ::= { cevModuleCommonCards 205 }

-- 2-port OC3c SFP Optics ATM Shared Port Adapter

cevSpa3xOC3AtmV2  OBJECT IDENTIFIER
    ::= { cevModuleCommonCards 206 }

-- 3-port OC3c SFP Optics ATM Shared Port Adapter

cevSpa1xOC12AtmV2  OBJECT IDENTIFIER
    ::= { cevModuleCommonCards 207 }

-- 1-port OC12c SFP Optics ATM Shared Port Adapter

cevNmTransOptSrvcEng1  OBJECT IDENTIFIER
    ::= { cevModuleCommonCards 208 }

-- Transport Performance Optimization NM Module (1GB DDRII) for Modular and Integrated Services Routers

cevAimTransOptSrvcEng1  OBJECT IDENTIFIER
    ::= { cevModuleCommonCards 209 }

-- Transport Performance Optimization AIM Module(512MB DDRII) for Modular and Integrated Services Routers

cevNmTransOptSrvcEng2  OBJECT IDENTIFIER
    ::= { cevModuleCommonCards 210 }

-- Transport Performance Optimization NM Module for Modular and Integrated Services Routers

cevAimTransOptSrvcEng2  OBJECT IDENTIFIER
    ::= { cevModuleCommonCards 211 }

-- Transport Performance Optimization AIM Module(1GB DDRII) for Modular and Integrated Services Routers

cevOnboardSe  OBJECT IDENTIFIER
    ::= { cevModuleCommonCards 212 }

-- On-board Integrated Service Engine

cevAimIpsK9  OBJECT IDENTIFIER
    ::= { cevModuleCommonCards 213 }

-- Cisco Intrusion Proctection System AIM Adapter

cevNmeApaModule  OBJECT IDENTIFIER
    ::= { cevModuleCommonCards 214 }

-- Integrated Service Engine for Application Performance Assurance.

cevHwicVdslPots  OBJECT IDENTIFIER
    ::= { cevModuleCommonCards 215 }

-- VDSL and ADSL modes over POTS(HWIC-1VDSL)

cevHwicVdslIsdn  OBJECT IDENTIFIER
    ::= { cevModuleCommonCards 216 }

-- VDSL and ADSL modes over ISDN(HWIC-1VDSLI)

cevWsIpsec3  OBJECT IDENTIFIER
    ::= { cevModuleCommonCards 217 }

-- IPSec Shared Port Adapter with DES/3DES/AES (WS-IPSEC-3)

cevHwic2as  OBJECT IDENTIFIER
    ::= { cevModuleCommonCards 218 }

-- High speed WAN Interface Card - Serial 2A/S

cevHwic2t  OBJECT IDENTIFIER
    ::= { cevModuleCommonCards 219 }

-- High speed Wan Interface Card - Serial (2T)

cevHwic1t  OBJECT IDENTIFIER
    ::= { cevModuleCommonCards 220 }

-- High speed Wan Interface Card - Serial (1T)

cevHwic1dsuT1  OBJECT IDENTIFIER
    ::= { cevModuleCommonCards 221 }

-- High speed Wan Interface Card with 1 Fractional T1 CSU/DSU port

cevDsx930418fk9  OBJECT IDENTIFIER
    ::= { cevModuleCommonCards 222 }

-- 18/4-port Multiservice FIPS Module

cevC7600SSC400  OBJECT IDENTIFIER
    ::= { cevModuleCommonCards 223 }

-- 2-subslot Services SPA Carrier-400

cevWSSSC600  OBJECT IDENTIFIER
    ::= { cevModuleCommonCards 224 }

-- 2-subslot Services SPA Carrier-600

cevSpa2pGeSynce  OBJECT IDENTIFIER
    ::= { cevModuleCommonCards 225 }

-- 2-port Synchronous Gigabit Ethernet Shared Port Adapter (SPA-2x1GE-SYNCE)

cevSpa2pChoc12Ds0  OBJECT IDENTIFIER
    ::= { cevModuleCommonCards 226 }

-- 2 port channelized OC12 to DS0 Shared Port Adapter (SPA-2XCHOC12/DS0)

cevAimVpnSsl1  OBJECT IDENTIFIER
    ::= { cevModuleCommonCards 227 }

-- AIM-VPN/SSL-1 card for Integrated Services Router

cevAimVpnSsl2  OBJECT IDENTIFIER
    ::= { cevModuleCommonCards 228 }

-- AIM-VPN/SSL-2 card for Integrated Services Router

cevAimVpnSsl3  OBJECT IDENTIFIER
    ::= { cevModuleCommonCards 229 }

-- AIM-VPN/SSL-3 card for Integrated Services Router

cevWsIpsec2  OBJECT IDENTIFIER
    ::= { cevModuleCommonCards 230 }

-- IPSec Shared Port Adapter with DES/3DES/AES (WS-IPSEC-2)

cevCVRX2SFP10G  OBJECT IDENTIFIER
    ::= { cevModuleCommonCards 231 }

-- 10G SFP+ port module in X2 form factor

cevHardDisk  OBJECT IDENTIFIER
    ::= { cevModuleCommonCards 232 }

-- Generic Hard Disk, can be of varied storage space (40, 60, 80 GB etc)

cevIsmSre300K9  OBJECT IDENTIFIER
    ::= { cevModuleCommonCards 234 }

-- Internal Service Module for Modular and Integrated Services Routers(ISM-SRE-300-K9)

cevSmSre700K9  OBJECT IDENTIFIER
    ::= { cevModuleCommonCards 237 }

-- Service Module for Modular and Integrated Services Routers(SM-SRE-700-K9)

cevSmSre900K9  OBJECT IDENTIFIER
    ::= { cevModuleCommonCards 239 }

-- Service Module for Modular and Integrated Services Routers(SM-SRE-900-K9)

cevSpaWmaSw  OBJECT IDENTIFIER
    ::= { cevModuleCommonCards 240 }

-- WebEx Node Shared Port Adaptor (SPA-WMA-K9)

cevHwic4ShdslEfm  OBJECT IDENTIFIER
    ::= { cevModuleCommonCards 242 }

-- HWIC G.SHDSL (4port) with EFM

cevAimAxp102  OBJECT IDENTIFIER
    ::= { cevModuleCommonCards 243 }

-- AXP Advanced Interface Module with 300MHz and 256MB RAM

cevAim2Axp104  OBJECT IDENTIFIER
    ::= { cevModuleCommonCards 244 }

-- AXP Advanced Interface Module 2 with 600MHz and 512MB RAM

cevNmAxp302  OBJECT IDENTIFIER
    ::= { cevModuleCommonCards 245 }

-- AXP Service Engine Network Module with 1GHz and 512MB RAM

cevNmAxp502  OBJECT IDENTIFIER
    ::= { cevModuleCommonCards 246 }

-- AXP Service Engine Network Module with 1GHz and 1GB RAM

cevNmAxp522  OBJECT IDENTIFIER
    ::= { cevModuleCommonCards 247 }

-- AXP Service Engine Network Module with 1.4GHz and 2GB RAM

cevWicGshdslEfm  OBJECT IDENTIFIER
    ::= { cevModuleCommonCards 248 }

-- A G.SHDSL WIC (WAN Interface Card) supporting EFM in C888 platform

cevNmeIss  OBJECT IDENTIFIER
    ::= { cevModuleCommonCards 249 }

-- Integrated Storage System 500GB HDD

cevNmeVmss216  OBJECT IDENTIFIER
    ::= { cevModuleCommonCards 250 }

-- Video Management and Storage System 16 streams 500GB HDD

cevNmeVmssHp32  OBJECT IDENTIFIER
    ::= { cevModuleCommonCards 251 }

-- Video Management and Storage System 32 streams 160GB HDD

cevNmeVmss2Hp32  OBJECT IDENTIFIER
    ::= { cevModuleCommonCards 252 }

-- Video Management and Storage System 32 streams 500GB HDD

cevNmeVmssHp16  OBJECT IDENTIFIER
    ::= { cevModuleCommonCards 253 }

-- Video Management and Storage System 16 streams 160GB HDD

cevNmeVmss16  OBJECT IDENTIFIER
    ::= { cevModuleCommonCards 254 }

-- Video Management and Storage System 16 streams 120GB HDD

cevNamWaasVirtualBlade  OBJECT IDENTIFIER
    ::= { cevModuleCommonCards 260 }

-- Cisco Network Analysis Module (NAM) Virtual Blade on WAAS appliance

cevSpaDsp  OBJECT IDENTIFIER
    ::= { cevModuleCommonCards 273 }

-- Digital Signal Processing Shared Port Adapter (SPA-DSP)

cevModuleCrs4S140GFabricCard  OBJECT IDENTIFIER
    ::= { cevModuleCommonCards 274 }

-- Cisco CRS Series 4 Slots Fabric Card / Single (140G)

cevModuleCrs8S140GFabricCard  OBJECT IDENTIFIER
    ::= { cevModuleCommonCards 275 }

-- Cisco CRS Series 8 Slots Fabric Card / Single (140G)

cevModuleCrs16S140GFabricCard  OBJECT IDENTIFIER
    ::= { cevModuleCommonCards 276 }

-- Cisco CRS Series 16 Slots Fabric Card / Single (140G)

cevModuleCrs16S140GFabricCardMulti  OBJECT IDENTIFIER
    ::= { cevModuleCommonCards 277 }

-- Cisco CRS Series 16 Slots Fabric Card / Multi (140G)

cevModuleCrs1140GFCCSFC  OBJECT IDENTIFIER
    ::= { cevModuleCommonCards 278 }

-- Cisco CRS Series Fabric Card Chassis Switch Fabric Card (140G)

cevC3KxNm1g  OBJECT IDENTIFIER
    ::= { cevModuleCommonCards 279 }

-- 4-Port SFP FRULink Module

cevC3KxNm10g  OBJECT IDENTIFIER
    ::= { cevModuleCommonCards 280 }

-- 2-Port SFP + 2-Port SFP/SFP+ FRULink Module

cevHwic2tC  OBJECT IDENTIFIER
    ::= { cevModuleCommonCards 282 }

-- High speed Wan Interface Card - Serial (2T)

cevHwic1tC  OBJECT IDENTIFIER
    ::= { cevModuleCommonCards 283 }

-- High speed Wan Interface Card - Serial (1T)

cevHwic4fesC  OBJECT IDENTIFIER
    ::= { cevModuleCommonCards 284 }

-- HWIC 4 Port Fast Ethernet Switch Cards

cevHwic9fesC  OBJECT IDENTIFIER
    ::= { cevModuleCommonCards 285 }

-- HWIC 9 Port Fast Ethernet Switch Cards

cevVwic2Mft1G703C  OBJECT IDENTIFIER
    ::= { cevModuleCommonCards 286 }

-- VWIC2-1MFT-G703 (1 Port) RJ-48 Multi-Flex Trunk - G.703

cevVwic2Mft2G703C  OBJECT IDENTIFIER
    ::= { cevModuleCommonCards 287 }

-- VWIC2-2MFT-G703 (2 Port)) RJ-48 Multi-Flex Trunk - G.703

cevNmEswitch16C  OBJECT IDENTIFIER
    ::= { cevModuleCommonCards 288 }

-- 16 Ports 10BaseT/100BaseTX EtherSwitch Network module with optional GE and IP Phone Line Power

cevC2960sStack  OBJECT IDENTIFIER
    ::= { cevModuleCommonCards 291 }

-- Cisco FlexStack Stacking Module

cevHardiskIdc  OBJECT IDENTIFIER
    ::= { cevModuleCommonCards 292 }

-- HDD IDC drive for ASR1001

cevEhwic4esg  OBJECT IDENTIFIER
    ::= { cevModuleCommonCards 293 }

-- 4 Port GE Non-POE EHWIC Switch

cevEhwicD8esg  OBJECT IDENTIFIER
    ::= { cevModuleCommonCards 294 }

-- 8 Port GE Non-POE EHWIC Switch

cevEhwicD8esgP  OBJECT IDENTIFIER
    ::= { cevModuleCommonCards 295 }

-- 8 Port GE POE EHWIC Switch

cevEhwic4esgP  OBJECT IDENTIFIER
    ::= { cevModuleCommonCards 296 }

-- 4 Port GE POE EHWIC Switch

cevVmssSmSre700K9  OBJECT IDENTIFIER
    ::= { cevModuleCommonCards 297 }

-- Video Management and Storage System on SRE-SM-700

cevVmssSmSre900K9  OBJECT IDENTIFIER
    ::= { cevModuleCommonCards 298 }

-- Video Management and Storage System on SRE-SM-900

cevIssSmSre700K9  OBJECT IDENTIFIER
    ::= { cevModuleCommonCards 299 }

-- Integrated Storage System on SRE-SM-700

cevIssSmSre900K9  OBJECT IDENTIFIER
    ::= { cevModuleCommonCards 300 }

-- Integrated Storage System on SRE-SM-900

cevModem3gGsm504A  OBJECT IDENTIFIER
    ::= { cevModuleCommonCards 301 }

-- Sierra Wireless 504-A

cevModem3gGsm504G  OBJECT IDENTIFIER
    ::= { cevModuleCommonCards 302 }

-- Sierra Wireless 504-G

cevCvrCfp4sfp10g  OBJECT IDENTIFIER
    ::= { cevModuleCommonCards 303 }

-- 4-port SFP+ port module in CFP form factor

cevModem3gCdma5728V  OBJECT IDENTIFIER
    ::= { cevModuleCommonCards 304 }

-- Sierra Wireless MC5728V(Dual-band EVDO Rev. A/Rev 0/1xRTT)

cevModem3gGsmMC8705  OBJECT IDENTIFIER
    ::= { cevModuleCommonCards 305 }

-- Sierra Wireless MC8705 modem(Quad-band HSPA+ and Quad-band GPRS/EDGE)

cevModem3gGsmMC8795  OBJECT IDENTIFIER
    ::= { cevModuleCommonCards 306 }

-- Sierra Wireless MC8795V  modem(Quad-band HSPA and Quad-band GPRS/EDGE)

cevModem3gGsmMc8705A  OBJECT IDENTIFIER
    ::= { cevModuleCommonCards 313 }

-- Sierra Wireless MC8705-A modem(Quad-band HSPA+ and Quad-band GPRS/EDGE)

cevHardDisk8541  OBJECT IDENTIFIER
    ::= { cevModuleCommonCards 314 }

-- Hard disk for Cisco Oe8541

cevHardDisk7571  OBJECT IDENTIFIER
    ::= { cevModuleCommonCards 315 }

-- Hard disk for Cisco Oe7571

cevHardDisk7541  OBJECT IDENTIFIER
    ::= { cevModuleCommonCards 316 }

-- Hard disk for Cisco Oe7541

cevHardDisk694  OBJECT IDENTIFIER
    ::= { cevModuleCommonCards 317 }

-- Hard disk for Cisco Oe694

cevHardDisk594  OBJECT IDENTIFIER
    ::= { cevModuleCommonCards 318 }

-- Hard disk for Cisco Oe594

cevHardDisk294  OBJECT IDENTIFIER
    ::= { cevModuleCommonCards 319 }

-- Hard disk for Cisco Oe294

cevModuleDIMM8541  OBJECT IDENTIFIER
    ::= { cevModuleCommonCards 320 }

-- DIMM for Oe8541

cevModuleDIMM7541  OBJECT IDENTIFIER
    ::= { cevModuleCommonCards 321 }

-- DIMM for Oe7541

cevModuleDIMM7571  OBJECT IDENTIFIER
    ::= { cevModuleCommonCards 322 }

-- DIMM for Oe7571

cevModuleDIMM294  OBJECT IDENTIFIER
    ::= { cevModuleCommonCards 323 }

-- DIMM for Oe294

cevModuleDIMM694  OBJECT IDENTIFIER
    ::= { cevModuleCommonCards 324 }

-- DIMM for Oe694

cevModuleDIMM594  OBJECT IDENTIFIER
    ::= { cevModuleCommonCards 325 }

-- DIMM for Oe594

cevModuleIOM294  OBJECT IDENTIFIER
    ::= { cevModuleCommonCards 328 }

-- IOM for Oe294

cevModuleIOM594  OBJECT IDENTIFIER
    ::= { cevModuleCommonCards 329 }

-- IOM for Oe594

cevModuleIOM694  OBJECT IDENTIFIER
    ::= { cevModuleCommonCards 330 }

-- IOM for Oe694

cevModuleIOM7541  OBJECT IDENTIFIER
    ::= { cevModuleCommonCards 331 }

-- IOM for Oe7541

cevModuleIOM7571  OBJECT IDENTIFIER
    ::= { cevModuleCommonCards 332 }

-- IOM for Oe7571

cevModuleIOM8541  OBJECT IDENTIFIER
    ::= { cevModuleCommonCards 333 }

-- IOM for Oe8541

cevIM8pGeCu  OBJECT IDENTIFIER
    ::= { cevModuleCommonCards 334 }

-- 8-port Gigabit Ethernet Copper based Interface Module

cevIM8pGeSFP  OBJECT IDENTIFIER
    ::= { cevModuleCommonCards 335 }

-- 8-port Gigabit Ethernet SFP based Interface Module

cevIM16pT1E1  OBJECT IDENTIFIER
    ::= { cevModuleCommonCards 336 }

-- 16-port T1/E1  Interface Module

cevIM1p10GeXfp  OBJECT IDENTIFIER
    ::= { cevModuleCommonCards 337 }

-- 1-port 10 Gigabit Ethernet XFP based Interface Module

cevIM4pOc3R1pOc12  OBJECT IDENTIFIER
    ::= { cevModuleCommonCards 338 }

-- 4-port OC3 or 1-port OC12 Interface Module

cevEp1p40GeQsfp  OBJECT IDENTIFIER
    ::= { cevModuleCommonCards 343 }

-- ASR 9000 1-port 40GE Modular Port Adapter

cevEp2p40GeQsfp  OBJECT IDENTIFIER
    ::= { cevModuleCommonCards 344 }

-- ASR 9000 2-port 40GE Modular Port Adapter

cevMpa2X10GE  OBJECT IDENTIFIER
    ::= { cevModuleCommonCards 350 }

-- ASR 9000 2-port 10GE Modular Port Adapter

cevMpa4X10GE  OBJECT IDENTIFIER
    ::= { cevModuleCommonCards 351 }

-- ASR 9000 4-port 10GE Modular Port Adapter

cevMpa20X1GE  OBJECT IDENTIFIER
    ::= { cevModuleCommonCards 352 }

-- ASR 9000 20-port 1GE Modular Port Adapter

cevMpa1X40GE  OBJECT IDENTIFIER
    ::= { cevModuleCommonCards 353 }

-- ASR 9000 1-port 40GE Modular Port Adapter

cevMpa2X40GE  OBJECT IDENTIFIER
    ::= { cevModuleCommonCards 354 }

-- ASR 9000 2-port 40GE Modular Port Adapter

cevModuleNic2x10GeSfp  OBJECT IDENTIFIER
    ::= { cevModuleCommonCards 359 }

-- Intel Niantic NIC 2x 10GE Sfp+ "2x Ten Gigabit Ethernet Controller"

cevModuleNic4x10GeSfp  OBJECT IDENTIFIER
    ::= { cevModuleCommonCards 360 }

-- Intel Niantic NIC 4x 10GE Sfp+ "4x Ten Gigabit Ethernet Controller"

cevModuleNic4x1GeSfp  OBJECT IDENTIFIER
    ::= { cevModuleCommonCards 361 }

-- Intel 4port NIC 4x 1GE Sfp "4x Gigabit Ethernet Controller"

cevModule4portNic4x1GeCu  OBJECT IDENTIFIER
    ::= { cevModuleCommonCards 362 }

-- Intel 4port NIC 4x 1GE Cu "4x Gigabit Ethernet Controller"

cevModule1xNitrox3  OBJECT IDENTIFIER
    ::= { cevModuleCommonCards 363 }

-- Cavium 1x Nitrox3 card 1x Security Acceleration Processor

cevModule4xNitrox3  OBJECT IDENTIFIER
    ::= { cevModuleCommonCards 364 }

-- Cavium 4x Nitrox3 card 4x Security Acceleration Processor

cevSpaHDwbdSfp  OBJECT IDENTIFIER
    ::= { cevModuleCommonCards 365 }

-- This is a Wideband SPA card which implements the Wideband protocol for CMTS, and which is upgrade of cevSpa24xwbdSfp

cevSpa8pT3E3Serial  OBJECT IDENTIFIER
    ::= { cevModuleCommonCards 366 }

-- 8-port T3/E3 Serial Shared Port Adapter (SPA-8XT3/E3)

cevSolidStateDisk8541  OBJECT IDENTIFIER
    ::= { cevModuleCommonCards 367 }

-- Solid State Disk for Cisco Oe8541

cevSolidStateDisk7541  OBJECT IDENTIFIER
    ::= { cevModuleCommonCards 368 }

-- Solid State Disk for Cisco Oe7541

cevSolidStateDisk7571  OBJECT IDENTIFIER
    ::= { cevModuleCommonCards 369 }

-- Solid State Disk for Cisco Oe7571

cevSolidStateDisk694  OBJECT IDENTIFIER
    ::= { cevModuleCommonCards 370 }

-- Solid State Disk for Cisco Oe694

cevSolidStateDisk594  OBJECT IDENTIFIER
    ::= { cevModuleCommonCards 371 }

-- Solid State Disk for Cisco Oe594

cevSolidStateDisk294  OBJECT IDENTIFIER
    ::= { cevModuleCommonCards 372 }

-- Solid State Disk for Cisco Oe294

cevWaveInlnGe4T  OBJECT IDENTIFIER
    ::= { cevModuleCommonCards 373 }

-- 4 port GE copper inline card

cevWaveInlnGe8T  OBJECT IDENTIFIER
    ::= { cevModuleCommonCards 374 }

-- 8 port GE copper inline card

cevWaveInlnGe4SX  OBJECT IDENTIFIER
    ::= { cevModuleCommonCards 375 }

-- 4 port GE SX fiber inline card

cevWave10Ge2SFP  OBJECT IDENTIFIER
    ::= { cevModuleCommonCards 376 }

-- 2 port 10GE SFP+ card

cevA9kMpa8X10GE  OBJECT IDENTIFIER
    ::= { cevModuleCommonCards 378 }

-- ASR 9000 8-port 10GE Modular Port Adapter

cevA9KMpa8X10GE  OBJECT IDENTIFIER
    ::= { cevModuleCommonCards 379 }

-- ASR 9000 8-port 10GE Modular Port Adapter

cevIom4GeInln  OBJECT IDENTIFIER
    ::= { cevModuleCommonCards 380 }

-- WAVE 4 port GE copper inline card

cevIom8GeInln  OBJECT IDENTIFIER
    ::= { cevModuleCommonCards 381 }

-- WAVE 8 port GE copper inline card

cevIom4GefInln  OBJECT IDENTIFIER
    ::= { cevModuleCommonCards 382 }

-- WAVE 4 port GE SX inline card

cevIom2X10Ge  OBJECT IDENTIFIER
    ::= { cevModuleCommonCards 383 }

-- WAVE 2 port 10GE SFP+ card

cevSfpH10GbCu5M  OBJECT IDENTIFIER
    ::= { cevModuleCommonCards 384 }

-- SFP+ DA CU Core0 Te1/0 IOM card

cevWaveScGe12T  OBJECT IDENTIFIER
    ::= { cevModuleCommonCards 385 }

-- AppNav IOM for WAVE - 12 port Gigabit Ethernet copper

cevWaveScGe12Sfp  OBJECT IDENTIFIER
    ::= { cevModuleCommonCards 386 }

-- AppNav IOM for WAVE - 12 port Gigabit Ethernet SFP

cevWaveSc10Ge4Sfp  OBJECT IDENTIFIER
    ::= { cevModuleCommonCards 387 }

-- AppNav IOM for WAVE-594 - 4 port 10 Gigabit Ethernet SFP+

cevWaveApnvGe12T  OBJECT IDENTIFIER
    ::= { cevModuleCommonCards 388 }

-- AppNav IOM for WAVE - 12 port Gigabit Ethernet copper

cevWaveApnvGe12Sfp  OBJECT IDENTIFIER
    ::= { cevModuleCommonCards 389 }

-- AppNav IOM for WAVE - 12 port Gigabit Ethernet SFP

cevWaveApnv10Ge4Sfp  OBJECT IDENTIFIER
    ::= { cevModuleCommonCards 390 }

-- AppNav IOM for WAVE-594 - 4 port 10 Gigabit Ethernet SFP+

cevIM14pSerial  OBJECT IDENTIFIER
    ::= { cevModuleCommonCards 407 }

-- 14 port serial interface module with 8 async and 6 sync/async ports

cevModulePseAsicPlim  OBJECT IDENTIFIER
    ::= { cevModuleCommonCards 445 }

-- Physical line interface module on the Network Processor Unit

cevModuleCisco60P10GeSFPPlusLsrLC  OBJECT IDENTIFIER
    ::= { cevModuleCommonCards 446 }

-- 4 Slice Card Supports 60x10 GBE ports with SFP+ optics LSR card

cevModuleCisco30P10GeSFPPlusLsrLC  OBJECT IDENTIFIER
    ::= { cevModuleCommonCards 447 }

-- 2 Slice Card Supports 30x10 GBE ports with SFP+ optics LSR card

cevModuleCisco15P10GeSFPPlusLsrLC  OBJECT IDENTIFIER
    ::= { cevModuleCommonCards 448 }

-- 1 Slice Card Supports 15x10 GBE ports with SFP+ optics LSR card

cevModuleCisco15P10GeSFPPlusLC  OBJECT IDENTIFIER
    ::= { cevModuleCommonCards 449 }

-- 1 Slice Card Supports 15x10 GBE ports with SFP+ optics

cevModuleCisco30P10GeSFPPlusLC  OBJECT IDENTIFIER
    ::= { cevModuleCommonCards 450 }

-- 2 Slice Card Supports 30x10 GBE ports with SFP+ optics

cevModuleCisco60P10GeSFPPlusLC  OBJECT IDENTIFIER
    ::= { cevModuleCommonCards 451 }

-- 4 Slice Card Supports 60x10 GBE ports with SFP+ optics

cevModuleVirtualBlade  OBJECT IDENTIFIER
    ::= { cevModuleCommonCards 452 }

-- Network Analysis Module Virtual Blade

cevModuleASA55125515ASAIC6GECUA  OBJECT IDENTIFIER
    ::= { cevModuleCommonCards 453 }

-- ASA 5512/15 Interface card unit with 6 Copper GE Ports

cevModuleASA5525ASAIC6GECUB  OBJECT IDENTIFIER
    ::= { cevModuleCommonCards 454 }

-- ASA 5525 Interface card unit with 6 Copper GE Ports

cevModuleASA55455555ASAIC6GECUC  OBJECT IDENTIFIER
    ::= { cevModuleCommonCards 455 }

-- ASA 5545/55 Interface card unit with 6 Copper GE Ports

cevModuleASA55125515ASAIC6GESFPA  OBJECT IDENTIFIER
    ::= { cevModuleCommonCards 456 }

-- ASA 5512/15 Interface card unit with 6 SFP GE Ports

cevModuleASA5525ASAIC6GESFPB  OBJECT IDENTIFIER
    ::= { cevModuleCommonCards 457 }

-- ASA 5525 Interface card unit with 6 SFP GE Ports

cevModuleASA55455555ASAIC6GESFPC  OBJECT IDENTIFIER
    ::= { cevModuleCommonCards 458 }

-- ASA 5545/55 Interface card unit with 6 SFP GE Ports

cevModuleNCS4KDCPWF  OBJECT IDENTIFIER
    ::= { cevModuleCommonCards 459 }

-- NCS 4016 DC Power Filter Module

cevModuleNCS4KECU  OBJECT IDENTIFIER
    ::= { cevModuleCommonCards 460 }

-- NCS 4K External Connection Unit

cevPEhwic4Esg  OBJECT IDENTIFIER
    ::= { cevModuleCommonCards 470 }

-- Four port 10/100/1000 Ethernet switch interface card

cevPEhwicD8Esg  OBJECT IDENTIFIER
    ::= { cevModuleCommonCards 471 }

-- Eight port 10/100/1000 Ethernet switch interface card

cevPWic1BStV3  OBJECT IDENTIFIER
    ::= { cevModuleCommonCards 472 }

-- 1-Port ISDN WAN Interface Card (dial and leased line)

cevPhwic1Adsl  OBJECT IDENTIFIER
    ::= { cevModuleCommonCards 473 }

-- 1-port ADSLoPOTS HWIC

cevPhwic1Adslm  OBJECT IDENTIFIER
    ::= { cevModuleCommonCards 474 }

-- 1-port ADSL HWIC w/Annex M

cevPHwic1Dsut1  OBJECT IDENTIFIER
    ::= { cevModuleCommonCards 475 }

-- 1-Port T1/Fractional T1 DSU/CSU WAN Interface Card

cevPHwic1t  OBJECT IDENTIFIER
    ::= { cevModuleCommonCards 476 }

-- 1-Port Serial WAN Interface Card

cevPHwic1as  OBJECT IDENTIFIER
    ::= { cevModuleCommonCards 477 }

-- 2-Port Async/Sync Serial WAN Interface Card

cevPHwic2Fe  OBJECT IDENTIFIER
    ::= { cevModuleCommonCards 478 }

-- Two 10/100 routed port HWIC

cevPHwic2t  OBJECT IDENTIFIER
    ::= { cevModuleCommonCards 479 }

-- 2-Port Serial WAN Interface Card

cevPIsmSre300K9  OBJECT IDENTIFIER
    ::= { cevModuleCommonCards 480 }

-- Internal Services Module (ISM) with Services Ready Engine
--   

-- cevModuleC36xxType cards are slot-cards specific to the c36xx platforms

cevModuleC36xxType  OBJECT IDENTIFIER
    ::= { cevModule 3 }

cevPmCpm1e2w  OBJECT IDENTIFIER
    ::= { cevModuleC36xxType 1 }

cevPmCpm2e2w  OBJECT IDENTIFIER
    ::= { cevModuleC36xxType 2 }

cevPmCpm1e1r2w  OBJECT IDENTIFIER
    ::= { cevModuleC36xxType 3 }

cevPmCt1Csu  OBJECT IDENTIFIER
    ::= { cevModuleC36xxType 4 }

cevPm2ct1Csu  OBJECT IDENTIFIER
    ::= { cevModuleC36xxType 5 }

cevPmCt1Dsx1  OBJECT IDENTIFIER
    ::= { cevModuleC36xxType 6 }

cevPm2ct1Dsx1  OBJECT IDENTIFIER
    ::= { cevModuleC36xxType 7 }

cevPmCe1Balanced  OBJECT IDENTIFIER
    ::= { cevModuleC36xxType 8 }

cevPm2ce1Balanced  OBJECT IDENTIFIER
    ::= { cevModuleC36xxType 9 }

cevPmCe1Unbalanced  OBJECT IDENTIFIER
    ::= { cevModuleC36xxType 10 }

cevPm2ce1Unbalanced  OBJECT IDENTIFIER
    ::= { cevModuleC36xxType 11 }

cevPm4bU  OBJECT IDENTIFIER
    ::= { cevModuleC36xxType 12 }

cevPm4bSt  OBJECT IDENTIFIER
    ::= { cevModuleC36xxType 13 }

cevPm8bU  OBJECT IDENTIFIER
    ::= { cevModuleC36xxType 14 }

cevPm8bSt  OBJECT IDENTIFIER
    ::= { cevModuleC36xxType 15 }

cevPm4as  OBJECT IDENTIFIER
    ::= { cevModuleC36xxType 16 }

cevPm8as  OBJECT IDENTIFIER
    ::= { cevModuleC36xxType 17 }

cevPm4e  OBJECT IDENTIFIER
    ::= { cevModuleC36xxType 18 }

cevPm1e  OBJECT IDENTIFIER
    ::= { cevModuleC36xxType 19 }

cevPmM4t  OBJECT IDENTIFIER
    ::= { cevModuleC36xxType 21 }

cevPm16a  OBJECT IDENTIFIER
    ::= { cevModuleC36xxType 22 }

cevPm32a  OBJECT IDENTIFIER
    ::= { cevModuleC36xxType 23 }

cevPmC36001fe  OBJECT IDENTIFIER
    ::= { cevModuleC36xxType 24 }

cevPmC3600Compression  OBJECT IDENTIFIER
    ::= { cevModuleC36xxType 25 }

cevPmDmodem  OBJECT IDENTIFIER
    ::= { cevModuleC36xxType 26 }

cevPm8admodem  OBJECT IDENTIFIER
    ::= { cevModuleC36xxType 27 }

cevPm16admodem  OBJECT IDENTIFIER
    ::= { cevModuleC36xxType 28 }

cevVpm2v  OBJECT IDENTIFIER
    ::= { cevModuleC36xxType 29 }

cevVpm4v  OBJECT IDENTIFIER
    ::= { cevModuleC36xxType 30 }

cevPmC36001feTx  OBJECT IDENTIFIER
    ::= { cevModuleC36xxType 31 }

cevPmC36001feFx  OBJECT IDENTIFIER
    ::= { cevModuleC36xxType 32 }

cevPm1fe1t1  OBJECT IDENTIFIER
    ::= { cevModuleC36xxType 33 }

cevPm1fe2t1  OBJECT IDENTIFIER
    ::= { cevModuleC36xxType 34 }

cevPm1fe1e1  OBJECT IDENTIFIER
    ::= { cevModuleC36xxType 35 }

cevPm1fe2e1  OBJECT IDENTIFIER
    ::= { cevModuleC36xxType 36 }

cevPm1fe1t1Csu  OBJECT IDENTIFIER
    ::= { cevModuleC36xxType 37 }

cevPm1fe2t1Csu  OBJECT IDENTIFIER
    ::= { cevModuleC36xxType 38 }

cevC36xx2feTx  OBJECT IDENTIFIER
    ::= { cevModuleC36xxType 39 }

-- Onboard 2FE Interfaces for c3660 chassis

cevPmOc3mm  OBJECT IDENTIFIER
    ::= { cevModuleC36xxType 40 }

-- ATM OC3 multimode Port Module

cevPmOc3mmVpd  OBJECT IDENTIFIER
    ::= { cevModuleC36xxType 41 }

-- ATM OC3 multimode Port Module with Voice Processing Deck

cevPmOc3smiVpd  OBJECT IDENTIFIER
    ::= { cevModuleC36xxType 42 }

-- ATM OC3 single mode intermediate reach Port Module with Voice Processing Deck

cevPmOc3smlVpd  OBJECT IDENTIFIER
    ::= { cevModuleC36xxType 43 }

-- ATM OC3 single mode long reach Port Module with Voice Processing Deck

cevPmOc3sml  OBJECT IDENTIFIER
    ::= { cevModuleC36xxType 44 }

-- ATM OC3 single mode long reach Port Module

cevPmOc3smi  OBJECT IDENTIFIER
    ::= { cevModuleC36xxType 45 }

-- ATM OC3 single mode intermediate reach Port Module

cevVic2fxoEu  OBJECT IDENTIFIER
    ::= { cevModuleC36xxType 46 }

-- 2 port Foreign eXchange Office Voice Interface Cards for most of Europe

cevVic2fxoM3  OBJECT IDENTIFIER
    ::= { cevModuleC36xxType 47 }

-- 2 port Foreign eXchange Office Voice Interface Cards for Australia

cevVic2fxoM4  OBJECT IDENTIFIER
    ::= { cevModuleC36xxType 48 }

-- 2 port Foreign eXchange Office Voice Interface Cards for Germany

cevVic2fxoM5  OBJECT IDENTIFIER
    ::= { cevModuleC36xxType 49 }

-- 2 port Foreign eXchange Office Voice Interface Cards for France

cevVic2fxoM6  OBJECT IDENTIFIER
    ::= { cevModuleC36xxType 50 }

-- 2 port Foreign eXchange Office Voice Interface Cards for Italy

cevVic2fxoM7  OBJECT IDENTIFIER
    ::= { cevModuleC36xxType 51 }

-- 2 port Foreign eXchange Office Voice Interface Cards for Portugal

cevVic2fxoM8  OBJECT IDENTIFIER
    ::= { cevModuleC36xxType 52 }

-- 2 port Foreign eXchange Office Voice Interface Cards for Singapore

cevVic2ST2086  OBJECT IDENTIFIER
    ::= { cevModuleC36xxType 53 }

-- 2 port Terminal Endpoint BRI S/T Voice interface daughter card

cevHdv  OBJECT IDENTIFIER
    ::= { cevModuleC36xxType 54 }

-- High Density Voice over IP network module

cevNm1fe2w  OBJECT IDENTIFIER
    ::= { cevModuleC36xxType 59 }

-- Network Module with 1 Fast Ethernet and 2 WIC/VIC interfaces

cevNm2fe2w  OBJECT IDENTIFIER
    ::= { cevModuleC36xxType 60 }

-- Network Module with 2 Fast Ethernet and 2 WIC/VIC interfaces

cevNm1fe1r2w  OBJECT IDENTIFIER
    ::= { cevModuleC36xxType 61 }

-- Network Module with 1 Fast Ethernet, 1 token ring, and 2 WIC/VIC interfaces

cevNm2w  OBJECT IDENTIFIER
    ::= { cevModuleC36xxType 62 }

-- Network Module with 2 WIC/VIC interfaces

cevC36xx1feTx  OBJECT IDENTIFIER
    ::= { cevModuleC36xxType 63 }

-- Onboard 1FE Interface for the c3660 chassis

cevAimLc4e1Compression  OBJECT IDENTIFIER
    ::= { cevModuleC36xxType 64 }

-- Lowcost 4 E-1 Compression AIM

cevVic2fxoM1  OBJECT IDENTIFIER
    ::= { cevModuleC36xxType 65 }

-- 2 port Foreign eXchange Office Voice Interface cards (Module 1) for North America

cevVic2fxoM2  OBJECT IDENTIFIER
    ::= { cevModuleC36xxType 68 }

-- 2 port Foreign eXchange Office Voice Interface Cards (Module 2) for Europe/Australia/New Zealand

cevPmDs3  OBJECT IDENTIFIER
    ::= { cevModuleC36xxType 69 }

-- ATM DS3 Port Module for 2600, 3600 series

cevPmE3  OBJECT IDENTIFIER
    ::= { cevModuleC36xxType 70 }

-- ATM E3 Port Module for 2600, 3600 series

cevVic2vpFxsDid  OBJECT IDENTIFIER
    ::= { cevModuleC36xxType 74 }

-- 2 Port Voice Interface Card for 26/3600 Platforms.  Ports can function as Foreign Exchange Station (FXS)or Direct Inward Dialing (DID) Voice Ports (VP)

cevVic2ST2086NtTe  OBJECT IDENTIFIER
    ::= { cevModuleC36xxType 75 }

-- Two port NT or TE Endpoint BRI S/T voice interface daughtercard

cevNmAic64  OBJECT IDENTIFIER
    ::= { cevModuleC36xxType 76 }

-- The new alarm interface card (AIC) network module with 64 monitoring points on the C26xx/C3600 platform

cevMIX366064  OBJECT IDENTIFIER
    ::= { cevModuleC36xxType 77 }

-- TDM Module that enables TDM switching on C3660 platform

cevWicAsync1am  OBJECT IDENTIFIER
    ::= { cevModuleC36xxType 78 }

-- WAN Interface Card - 1 Port Analog Modem

cevWicAsync2am  OBJECT IDENTIFIER
    ::= { cevModuleC36xxType 79 }

-- WAN Interface Card - Dual Analog Modem

cevAim4Dsps  OBJECT IDENTIFIER
    ::= { cevModuleC36xxType 81 }

-- DSP only AIM with 4 DSPs

cevHdaNm4fxs  OBJECT IDENTIFIER
    ::= { cevModuleC36xxType 82 }

-- High Density Analog Voice Module

cevC2610M  OBJECT IDENTIFIER
    ::= { cevModuleC36xxType 84 }

-- c2600M with 1 integrated ethernet interface

cevC2611M  OBJECT IDENTIFIER
    ::= { cevModuleC36xxType 85 }

-- c2600M with 2 integrated ethernet interfaces

cevNm1t3e3  OBJECT IDENTIFIER
    ::= { cevModuleC36xxType 91 }

-- One port Clear T3/E3 Network Module

cevNm1ct3e3  OBJECT IDENTIFIER
    ::= { cevModuleC36xxType 92 }

-- One port Channelized T3/E3 Network Module

cevNm8ct1e1  OBJECT IDENTIFIER
    ::= { cevModuleC36xxType 93 }

-- Eight port Channelized T1/E1 Network Module

cevHdaEm4fxo  OBJECT IDENTIFIER
    ::= { cevModuleC36xxType 94 }

-- 4-port FXO Expansion Module for High Density Analog Voice Interface Daughtercard

cevNm16AS  OBJECT IDENTIFIER
    ::= { cevModuleC36xxType 95 }

-- 16 port Async/Sync Network Module provides low speed serial interface for the MAR's family of platforms

cevNm1ct1e1Pri  OBJECT IDENTIFIER
    ::= { cevModuleC36xxType 102 }

-- One port Primary Rate Interface (PRI)  Channelized T1/E1 Network Module

cevNm2ct1e1Pri  OBJECT IDENTIFIER
    ::= { cevModuleC36xxType 103 }

-- Two port Primary Rate Interface (PRI)  Channelized T1/E1 Network Module

cevNmCeoip4t1e1  OBJECT IDENTIFIER
    ::= { cevModuleC36xxType 104 }

-- Four port T1/E1 Circuit Emulation over IP network module

cevNmCeoip4Serial  OBJECT IDENTIFIER
    ::= { cevModuleC36xxType 105 }

-- Four port Serial Interface Circuit Emulation over IP network module

cevNm1aOc3mmEp  OBJECT IDENTIFIER
    ::= { cevModuleC36xxType 106 }

-- Enhanced Performance ATM OC3, multimode network module

cevNm1aOc3smiEp  OBJECT IDENTIFIER
    ::= { cevModuleC36xxType 107 }

-- Enhanced Performance ATM OC3, intermediate reach single mode network module

cevNm1aOc3smlEp  OBJECT IDENTIFIER
    ::= { cevModuleC36xxType 108 }

-- Enhanced Performance ATM OC3, long reach single mode network module

cevNmCids  OBJECT IDENTIFIER
    ::= { cevModuleC36xxType 109 }

-- Intrusion Detection Sensor Module in NM form factor for 36xx/37xx/26xx family branch routers

cevHwic1GeSfp  OBJECT IDENTIFIER
    ::= { cevModuleC36xxType 119 }

-- Single port Gigabit Ethernet high-speed WAN interface card (HWIC) with Small Formfactor Pluggable (SFP) transceiver

cevPortHdDsp  OBJECT IDENTIFIER
    ::= { cevModuleC36xxType 120 }

-- 5510 Digital Signal Processor on NM-HD-1V,NM-HD-2V and NM-HD-2VE

cevHdv2port0  OBJECT IDENTIFIER
    ::= { cevModuleC36xxType 121 }

-- High Density Network module-2 with no onboard interface

cevHdv2port2  OBJECT IDENTIFIER
    ::= { cevModuleC36xxType 122 }

-- High Density Network module-2 with onboard two port T1/E1 interface

cevHdv2port1  OBJECT IDENTIFIER
    ::= { cevModuleC36xxType 123 }

-- High Density Network module-2 with onboard one port T1/E1 interface

cevNmAtm25  OBJECT IDENTIFIER
    ::= { cevModuleC36xxType 124 }

-- 25 Mbits/sec ATM Port Module

cevNmNam  OBJECT IDENTIFIER
    ::= { cevModuleC36xxType 125 }

-- Network Analysis Module (NAM) network module for the 2600/3600/3700 router families

cevNm8amV2  OBJECT IDENTIFIER
    ::= { cevModuleC36xxType 126 }

-- 8 Port Analog Modem Network Module Version 2

cevNm16amV2  OBJECT IDENTIFIER
    ::= { cevModuleC36xxType 127 }

-- 16 Port Analog Modem Network Module Version 2

cevCpuC28112fe  OBJECT IDENTIFIER
    ::= { cevModuleC36xxType 129 }

-- 2811 Motherboard with two integrated fast ethernets and integrated VPN

cevCpuC28212ge  OBJECT IDENTIFIER
    ::= { cevModuleC36xxType 130 }

-- 2821 Motherboard with two integrated gigabit ethernets and integrated VPN

cevCpuC28512ge  OBJECT IDENTIFIER
    ::= { cevModuleC36xxType 131 }

-- 2851 Motherboard with two integrated gigabit ethernets and integrated VPN

cevHWicSerial4t  OBJECT IDENTIFIER
    ::= { cevModuleC36xxType 132 }

-- High Speed Wan Interface Card with 4 serial ports(HWIC-4T)

cevHWicSerial4as  OBJECT IDENTIFIER
    ::= { cevModuleC36xxType 133 }

-- High Speed Wan Interface Card with 4 low speed sync/async serial ports(HWIC-4A/S)

cevHWicSerial8as  OBJECT IDENTIFIER
    ::= { cevModuleC36xxType 134 }

-- High Speed Wan Interface Card with 8 low speed RS232 sync/async serial ports(HWIC-8A/S)

cevHWicSerial8a  OBJECT IDENTIFIER
    ::= { cevModuleC36xxType 135 }

-- High Speed Wan Interface card with 8 RS232 async port(HWIC-8A)

cevHWicSerial16a  OBJECT IDENTIFIER
    ::= { cevModuleC36xxType 136 }

-- High Speed Wan Interface card with 16 RS232 async ports(HWIC-16A)

cevNm1AOc3Pom  OBJECT IDENTIFIER
    ::= { cevModuleC36xxType 137 }

-- Single port ATM OC3 network module with POM

cevHWic1DOCSIS20CableModem  OBJECT IDENTIFIER
    ::= { cevModuleC36xxType 146 }

-- High Speed Wan Interface card with 1 DOCSIS 2.0 cable modem port(HWIC-1CM)

cevNm8ce1t1Pri  OBJECT IDENTIFIER
    ::= { cevModuleC36xxType 148 }

-- 8 port T1/E1 clear channel and channelized NM

cevHWic4t1e1  OBJECT IDENTIFIER
    ::= { cevModuleC36xxType 149 }

-- 4 port T1/E1 clear channel HWIC

cevHWic2ce1t1Pri  OBJECT IDENTIFIER
    ::= { cevModuleC36xxType 150 }

-- 2 port T1/E1 channelized/PRI HWIC

cevHWic1ce1t1Pri  OBJECT IDENTIFIER
    ::= { cevModuleC36xxType 151 }

-- 1 port T1/E1 channelized/PRI HWIC

cevHWic1DOCSIS20CableModemEJ  OBJECT IDENTIFIER
    ::= { cevModuleC36xxType 152 }

-- High Speed Wan Interface card with 1 Euro-DOCSIS/J-DOCSIS 2.0 cable modem port(HWIC-1CM)

cevHwic1t1e1  OBJECT IDENTIFIER
    ::= { cevModuleC36xxType 154 }

-- 1 port (2 channel) T1/E1 HWIC

cevHwic4Shdsl  OBJECT IDENTIFIER
    ::= { cevModuleC36xxType 157 }

-- HWIC G.SHDSL (4 port) with annex F&G and IMA.

cevHwic2Shdsl  OBJECT IDENTIFIER
    ::= { cevModuleC36xxType 158 }

-- HWIC G.SHDSL (2 port) with annex F&G

cevNmRvpnSterra  OBJECT IDENTIFIER
    ::= { cevModuleC36xxType 159 }

-- Russia S-Terra VPN Module

cevNmRvpn  OBJECT IDENTIFIER
    ::= { cevModuleC36xxType 160 }

-- Special Services Engine for Modular and Integrated Services Routers

cevNmSpclSrvcEng  OBJECT IDENTIFIER
    ::= { cevModuleC36xxType 161 }

-- Special Services Engine for ISR routers

cevNmIntgrtdSrvcEng2  OBJECT IDENTIFIER
    ::= { cevModuleC36xxType 162 }

-- Integrated Service Engine2 for ISR router

cevHWIC1Ser  OBJECT IDENTIFIER
    ::= { cevModuleC36xxType 163 }

-- High Speed Wan Interface Card with 1 serial ports(HWIC-1SER)

cevHWIC2Ser  OBJECT IDENTIFIER
    ::= { cevModuleC36xxType 164 }

-- High Speed Wan Interface Card with 2 serial ports(HWIC-2SER)

cevInternalServiceModuleAIM  OBJECT IDENTIFIER
    ::= { cevModuleC36xxType 165 }

-- Internal Service Module AIM for Integrated Services Routers

cevSm1nm  OBJECT IDENTIFIER
    ::= { cevModuleC36xxType 167 }

-- Service Module to Network Module Adapter

cevSm2k15Es1GePoe  OBJECT IDENTIFIER
    ::= { cevModuleC36xxType 168 }

-- EtherSwitch Service Module Layer2 + PoE + 15 10/100 + 1 10/100/1000

cevSm3k15Es1GePoe  OBJECT IDENTIFIER
    ::= { cevModuleC36xxType 169 }

-- EtherSwitch Service Module Layer3 + PoE + 15 10/100 + 1 10/100/1000

cevSm3k16GePoe  OBJECT IDENTIFIER
    ::= { cevModuleC36xxType 170 }

-- EtherSwitch Service Module Layer3 + PoE + 16 10/100/1000

cevSm2k23Es1Ge  OBJECT IDENTIFIER
    ::= { cevModuleC36xxType 171 }

-- EtherSwitch Service Module Layer2 + no PoE + 23 10/100 + 1 10/100/1000

cevSm2k23Es1GePoe  OBJECT IDENTIFIER
    ::= { cevModuleC36xxType 172 }

-- EtherSwitch Service Module Layer2 + PoE + 23 10/100 + 1 10/100/1000

cevSm3k23Es1GePoe  OBJECT IDENTIFIER
    ::= { cevModuleC36xxType 173 }

-- EtherSwitch Service Module Layer3 + PoE + 23 10/100 + 1 10/100/1000

cevSm3k24GePoe  OBJECT IDENTIFIER
    ::= { cevModuleC36xxType 174 }

-- EtherSwitch Service Module Layer3 + PoE + 24 10/100/1000

cevSmXd2k48Es2SFP  OBJECT IDENTIFIER
    ::= { cevModuleC36xxType 175 }

-- EtherSwitch Service Module Layer2 + no PoE + 48 10/100 + 2 SFP

cevSmXd3k48Es2SFPPoe  OBJECT IDENTIFIER
    ::= { cevModuleC36xxType 176 }

-- EtherSwitch Service Module Layer3 + PoE + 48 10/100 + 2 SFP

cevSmXd3k48Ge2SFPPoe  OBJECT IDENTIFIER
    ::= { cevModuleC36xxType 177 }

-- EtherSwitch Service ModuleLayer3 + PoE + 48 10/100/1000 + 2 SFP

cevHwic4ce1t1Pri  OBJECT IDENTIFIER
    ::= { cevModuleC36xxType 180 }

-- 4 port T1/E1 channelized/PRI HWIC

cevEHwic1GeSfpCu  OBJECT IDENTIFIER
    ::= { cevModuleC36xxType 181 }

-- Single Port Gigabit Ethernet Extended High-Speed Wan Interface Card with either onboard cu port or SFP

cevEhwic3gEvdo  OBJECT IDENTIFIER
    ::= { cevModuleC36xxType 182 }

-- 3G EHWIC DuoBand EVDO Rev A/Rel 0/1xRTT and GPS

cevEhwic3gHspaU  OBJECT IDENTIFIER
    ::= { cevModuleC36xxType 183 }

-- 3G EHWIC QuadBand HSPA/UMTS QuadBand EDGE/GPRS and GPS

cevSm1pa  OBJECT IDENTIFIER
    ::= { cevModuleC36xxType 184 }

-- Service module to Port adapter

cevSm1Stm1Smi  OBJECT IDENTIFIER
    ::= { cevModuleC36xxType 185 }

-- 1 port multichannel STM-1 single mode service module

cevSm1Stm1Mm  OBJECT IDENTIFIER
    ::= { cevModuleC36xxType 186 }

-- 1 port multichannel STM-1 multimode service module

cevEhwic3gHspa7  OBJECT IDENTIFIER
    ::= { cevModuleC36xxType 187 }

-- 3G EHWIC QuadBand HSPA+R7/HSPA/UMTS QuadBand EDGE/GPRS and GPS

cevIsmVpnSsl3  OBJECT IDENTIFIER
    ::= { cevModuleC36xxType 188 }

-- Internal Service Module for VPN and SSL feature acceleration including Suite B Crypto support on Cisco 3900 routers

cevIsmVpnSsl2  OBJECT IDENTIFIER
    ::= { cevModuleC36xxType 189 }

-- Internal Service Module for VPN and SSL feature acceleration including Suite B Crypto support on Cisco 2900 routers

cevIsmVpnSsl1  OBJECT IDENTIFIER
    ::= { cevModuleC36xxType 190 }

-- Service Module for VPN and SSL feature acceleration including Suite B Crypto support on Cisco 1941 routers

cevEhwic3gHspa7A  OBJECT IDENTIFIER
    ::= { cevModuleC36xxType 191 }

-- 3G WWAN EHWIC-QuadBand HSPA+R7/HSPA/UMTS QuadBand EDGE/GPRS and GPS for AT&T

cevEhwic4gLteA  OBJECT IDENTIFIER
    ::= { cevModuleC36xxType 193 }

-- 4G WWAN EHWIC - North America Multimode LTE/DC-HSPA+/HSPA+/HSPA/UMTS/EDGE/GPRS

cevEhwic4gLteG  OBJECT IDENTIFIER
    ::= { cevModuleC36xxType 194 }

-- 4G WWAN EHWIC - Global Multimode LTE/DC-HSPA+/HSPA+/HSPA/UMTS/EDGE/GPRS

cevEhwic4gLteV  OBJECT IDENTIFIER
    ::= { cevModuleC36xxType 195 }

-- 4G WWAN EHWIC - Verizon Multimode LTE/eHRPD/EVDO RevA/Rev0/1xRTT

cevSm1T3E3  OBJECT IDENTIFIER
    ::= { cevModuleC36xxType 196 }

-- 1 port clear channel T3/E3 SM

cevSM32A  OBJECT IDENTIFIER
    ::= { cevModuleC36xxType 197 }

-- 32-port Asynchronous Interface Service Module for ISR G2s (c39XX)

cevEhwic4gLteJp  OBJECT IDENTIFIER
    ::= { cevModuleC36xxType 210 }

-- 4G WWAN EHWIC - Japan Multimode LTE/DC-HSPA+/HSPA+/HSPA/UMTS/EDGE/GPRS

cevEhwic4gLteBe  OBJECT IDENTIFIER
    ::= { cevModuleC36xxType 211 }

-- 4G WWAN EHWIC - Canada Bell Multimode LTE/DC-HSPA+/HSPA+/HSPA/UMTS/EDGE/GPRS

cevPEhwic1GeSfpCu  OBJECT IDENTIFIER
    ::= { cevModuleC36xxType 212 }

-- EHWIC 1 port dual mode SFP(100M/1G) or GE(10M/100M/1G)

cevPEhwic3gHspa7  OBJECT IDENTIFIER
    ::= { cevModuleC36xxType 213 }

-- (non-US) 3.7G HSPA+ Release 7 EHWIC w/ SMS/GPS (MC8705)

cevPHwicSerial16a  OBJECT IDENTIFIER
    ::= { cevModuleC36xxType 214 }

-- 16-Port Async HWIC

cevPhwic1Ce1T1Pri  OBJECT IDENTIFIER
    ::= { cevModuleC36xxType 215 }

-- 1 port channelized T1/E1 and PRI HWIC (data only)

cevPHwic2Ce1t1Pri  OBJECT IDENTIFIER
    ::= { cevModuleC36xxType 216 }

-- 2 port channelized T1/E1, and PRI HWIC (data only)

cevPHwicSerial4As  OBJECT IDENTIFIER
    ::= { cevModuleC36xxType 217 }

-- 4-Port Async/Sync Serial HWIC

cevPHwicSerial4t  OBJECT IDENTIFIER
    ::= { cevModuleC36xxType 218 }

-- 4-Port Serial HWIC

cevPHwic4T1E1  OBJECT IDENTIFIER
    ::= { cevModuleC36xxType 219 }

-- 4 port clear channel T1/E1 HWIC

cevPHwicSerial8a  OBJECT IDENTIFIER
    ::= { cevModuleC36xxType 220 }

-- 8-Port Async HWIC

cevPHwicSerial8as  OBJECT IDENTIFIER
    ::= { cevModuleC36xxType 221 }

-- 8-Port Async/Sync Serial HWIC, EIA-232

cevPIsmVpn29  OBJECT IDENTIFIER
    ::= { cevModuleC36xxType 222 }

-- 3DES/AES/SUITE-B VPN Encryption module

cevPVic2Fxo2  OBJECT IDENTIFIER
    ::= { cevModuleC36xxType 223 }

-- Two-port Voice Interface Card - FXO (Universal)

cevPVic2Fxo4  OBJECT IDENTIFIER
    ::= { cevModuleC36xxType 224 }

-- Four-port Voice Interface Card - FXO (Universal)

cevModuleVipPortAdapters  OBJECT IDENTIFIER
    ::= { cevModule 4 }

cevPa1fe  OBJECT IDENTIFIER
    ::= { cevModuleVipPortAdapters 1 }

cevPa8e  OBJECT IDENTIFIER
    ::= { cevModuleVipPortAdapters 2 }

cevPa4e  OBJECT IDENTIFIER
    ::= { cevModuleVipPortAdapters 3 }

cevPa5e  OBJECT IDENTIFIER
    ::= { cevModuleVipPortAdapters 4 }

cevPa4t  OBJECT IDENTIFIER
    ::= { cevModuleVipPortAdapters 5 }

cevPa4r  OBJECT IDENTIFIER
    ::= { cevModuleVipPortAdapters 6 }

cevPaFddi  OBJECT IDENTIFIER
    ::= { cevModuleVipPortAdapters 7 }

cevSaEncryption  OBJECT IDENTIFIER
    ::= { cevModuleVipPortAdapters 8 }

cevPaAh1t  OBJECT IDENTIFIER
    ::= { cevModuleVipPortAdapters 9 }

cevPaAh2t  OBJECT IDENTIFIER
    ::= { cevModuleVipPortAdapters 10 }

cevPaA8tV35  OBJECT IDENTIFIER
    ::= { cevModuleVipPortAdapters 12 }

cevPa1feTxIsl  OBJECT IDENTIFIER
    ::= { cevModuleVipPortAdapters 13 }

cevPa1feFxIsl  OBJECT IDENTIFIER
    ::= { cevModuleVipPortAdapters 14 }

cevPa1feTxNisl  OBJECT IDENTIFIER
    ::= { cevModuleVipPortAdapters 15 }

cevSaCompression  OBJECT IDENTIFIER
    ::= { cevModuleVipPortAdapters 16 }

cevPaAtmLite1  OBJECT IDENTIFIER
    ::= { cevModuleVipPortAdapters 17 }

cevPaCt3  OBJECT IDENTIFIER
    ::= { cevModuleVipPortAdapters 18 }

cevPaOc3smMuxCbrt1  OBJECT IDENTIFIER
    ::= { cevModuleVipPortAdapters 19 }

cevPaOc3smMuxCbr120e1  OBJECT IDENTIFIER
    ::= { cevModuleVipPortAdapters 20 }

cevPaOc3smMuxCbr75e1  OBJECT IDENTIFIER
    ::= { cevModuleVipPortAdapters 21 }

cevPaOc3mmMuxCbrt1  OBJECT IDENTIFIER
    ::= { cevModuleVipPortAdapters 22 }

cevPaOc3mmMuxCbr120e1  OBJECT IDENTIFIER
    ::= { cevModuleVipPortAdapters 23 }

cevPaOc3mmMuxCbr75e1  OBJECT IDENTIFIER
    ::= { cevModuleVipPortAdapters 24 }

cevPaDs3MuxCbrt1  OBJECT IDENTIFIER
    ::= { cevModuleVipPortAdapters 25 }

cevPaE3MuxCbr120e1  OBJECT IDENTIFIER
    ::= { cevModuleVipPortAdapters 26 }

cevPaE3smMuxCbr75e1  OBJECT IDENTIFIER
    ::= { cevModuleVipPortAdapters 27 }

cevPa8bSt  OBJECT IDENTIFIER
    ::= { cevModuleVipPortAdapters 28 }

cevPa4bU  OBJECT IDENTIFIER
    ::= { cevModuleVipPortAdapters 29 }

cevPaFddiFd  OBJECT IDENTIFIER
    ::= { cevModuleVipPortAdapters 30 }

cevPaJt2  OBJECT IDENTIFIER
    ::= { cevModuleVipPortAdapters 31 }

cevPaPosdw  OBJECT IDENTIFIER
    ::= { cevModuleVipPortAdapters 32 }

cevPa4me1Bal  OBJECT IDENTIFIER
    ::= { cevModuleVipPortAdapters 33 }

cevPa2ce1Balanced  OBJECT IDENTIFIER
    ::= { cevModuleVipPortAdapters 34 }

cevPa2ct1  OBJECT IDENTIFIER
    ::= { cevModuleVipPortAdapters 35 }

cevPa1vg  OBJECT IDENTIFIER
    ::= { cevModuleVipPortAdapters 36 }

cevPaAtmdxDs3  OBJECT IDENTIFIER
    ::= { cevModuleVipPortAdapters 37 }

cevPaAtmdxE3  OBJECT IDENTIFIER
    ::= { cevModuleVipPortAdapters 38 }

cevPaAtmdxSmlOc3  OBJECT IDENTIFIER
    ::= { cevModuleVipPortAdapters 39 }

cevPaAtmdxSmiOc3  OBJECT IDENTIFIER
    ::= { cevModuleVipPortAdapters 40 }

cevPaAtmdxMmOc3  OBJECT IDENTIFIER
    ::= { cevModuleVipPortAdapters 41 }

cevPaA8tX21  OBJECT IDENTIFIER
    ::= { cevModuleVipPortAdapters 42 }

cevPaA8tRs232  OBJECT IDENTIFIER
    ::= { cevModuleVipPortAdapters 43 }

cevPa4me1Unbal  OBJECT IDENTIFIER
    ::= { cevModuleVipPortAdapters 44 }

cevPa4rFdx  OBJECT IDENTIFIER
    ::= { cevModuleVipPortAdapters 45 }

cevPa1e3  OBJECT IDENTIFIER
    ::= { cevModuleVipPortAdapters 46 }

cevPa2e3  OBJECT IDENTIFIER
    ::= { cevModuleVipPortAdapters 47 }

cevPa1t3  OBJECT IDENTIFIER
    ::= { cevModuleVipPortAdapters 48 }

cevPa2t3  OBJECT IDENTIFIER
    ::= { cevModuleVipPortAdapters 49 }

cevPa2ce1Unbalanced  OBJECT IDENTIFIER
    ::= { cevModuleVipPortAdapters 50 }

cevPa14eSwitch  OBJECT IDENTIFIER
    ::= { cevModuleVipPortAdapters 51 }

cevas58001fedsi  OBJECT IDENTIFIER
    ::= { cevModuleVipPortAdapters 52 }

cevPa1feFxNisl  OBJECT IDENTIFIER
    ::= { cevModuleVipPortAdapters 53 }

cevPaIo1fe  OBJECT IDENTIFIER
    ::= { cevModuleVipPortAdapters 54 }

cevPaIo  OBJECT IDENTIFIER
    ::= { cevModuleVipPortAdapters 55 }

cevPa2feTx  OBJECT IDENTIFIER
    ::= { cevModuleVipPortAdapters 56 }

cevPa2feFx  OBJECT IDENTIFIER
    ::= { cevModuleVipPortAdapters 57 }

cevPaGe  OBJECT IDENTIFIER
    ::= { cevModuleVipPortAdapters 59 }

-- Gigabit Ethernet Port Adapter

cevPaPosswSm  OBJECT IDENTIFIER
    ::= { cevModuleVipPortAdapters 60 }

-- Single Width POS (Packet Over Sonet) Port Adapter with Singlemode Fiber

cevPaPosswMm  OBJECT IDENTIFIER
    ::= { cevModuleVipPortAdapters 61 }

-- Single Width POS (Packet Over Sonet) Port Adapter with Multimode Fiber

cevPaPosswLr  OBJECT IDENTIFIER
    ::= { cevModuleVipPortAdapters 62 }

-- Single Width POS (Packet Over Sonet) Port Adapter with Long Range Fiber

cevPa4ct1Csu  OBJECT IDENTIFIER
    ::= { cevModuleVipPortAdapters 63 }

-- 4-port channelized T1 with CSU (Channel Service Unit)

cevPa8ct1Csu  OBJECT IDENTIFIER
    ::= { cevModuleVipPortAdapters 64 }

-- 8-port channelized T1 with CSU (Channel Service Unit)

cevPa8ct1  OBJECT IDENTIFIER
    ::= { cevModuleVipPortAdapters 65 }

-- 8-port channelized T1

cevPa8ce1  OBJECT IDENTIFIER
    ::= { cevModuleVipPortAdapters 66 }

-- 8-port channelized E1

cevPaVxc2t1e1  OBJECT IDENTIFIER
    ::= { cevModuleVipPortAdapters 67 }

-- 2 port T1/E1 voice port adapter with 30 DSP's

cevPaVxb2t1e1  OBJECT IDENTIFIER
    ::= { cevModuleVipPortAdapters 68 }

-- 2 port T1/E1 voice port adapter with 12 DSP's

cevPaAtmOc12Mm  OBJECT IDENTIFIER
    ::= { cevModuleVipPortAdapters 69 }

-- Multimode ATM OC-12 Port Adapter

cevPaAtmOc12Smi  OBJECT IDENTIFIER
    ::= { cevModuleVipPortAdapters 70 }

-- Singlemode ATM OC-12 Intermediate reach Port Adapter

cevPaMct3  OBJECT IDENTIFIER
    ::= { cevModuleVipPortAdapters 71 }

-- Multichannel DS3 single port adapter

cevPaMc2t3  OBJECT IDENTIFIER
    ::= { cevModuleVipPortAdapters 72 }

-- Multichannel DS3 dual port adapter

cevPa1t3Plus  OBJECT IDENTIFIER
    ::= { cevModuleVipPortAdapters 73 }

-- Improved one port serial T3 plus port adapter

cevPa2t3Plus  OBJECT IDENTIFIER
    ::= { cevModuleVipPortAdapters 74 }

-- Improved 2 port serial T3 plus port adapter

cevPaPosOc12Mm  OBJECT IDENTIFIER
    ::= { cevModuleVipPortAdapters 75 }

-- OC-12 Packet Over SONET Port Adapter, Multi-Mode fiber

cevPaPosOc12Sm  OBJECT IDENTIFIER
    ::= { cevModuleVipPortAdapters 76 }

-- OC-12 Packet Over SONET Port Adapter, Single Mode fiber

cevPaImaT1  OBJECT IDENTIFIER
    ::= { cevModuleVipPortAdapters 77 }

-- Implements IMA functionality for the 7200/7500 platform for a T1

cevPaImaE1  OBJECT IDENTIFIER
    ::= { cevModuleVipPortAdapters 78 }

-- Implements IMA functionality for the 7200/7500 platform for an E1

cevSrpPaOc12Mm  OBJECT IDENTIFIER
    ::= { cevModuleVipPortAdapters 79 }

-- SRP OC-12/STM-4 Multimode Port Adapter for 7000 series

cevSrpPaOc12SmIr  OBJECT IDENTIFIER
    ::= { cevModuleVipPortAdapters 80 }

-- SRP OC-12/STM-4 Single Mode Intermediate Reach Port Adapter for 7000 series

cevSrpPaOc12Lr  OBJECT IDENTIFIER
    ::= { cevModuleVipPortAdapters 81 }

-- SRP OC-12/STM-4 Single Mode Long Reach Port Adapter for 7000 series

cevPa2ct1Csu  OBJECT IDENTIFIER
    ::= { cevModuleVipPortAdapters 82 }

-- 2 port multichannel T1 port adapter with built in csu/dsu for the 7200, 7500, and rsp7000 platforms

cevPa2ce1  OBJECT IDENTIFIER
    ::= { cevModuleVipPortAdapters 83 }

-- 2 port multichannel E1 port adapter for the 7200, 7500, and rsp7000 platforms

cevPaMcx2te1  OBJECT IDENTIFIER
    ::= { cevModuleVipPortAdapters 84 }

-- 2 port, software configurable Multichannel T1/E1 with TDM Port Adapter

cevPaMcx4te1  OBJECT IDENTIFIER
    ::= { cevModuleVipPortAdapters 85 }

-- 4 port, software configurable Multichannel T1/E1 with TDM Port Adapter

cevPaMcx8te1  OBJECT IDENTIFIER
    ::= { cevModuleVipPortAdapters 86 }

-- 8 port, software configurable Multichannel T1/E1 with TDM Port Adapter

cevSrpPaOc12SmXr  OBJECT IDENTIFIER
    ::= { cevModuleVipPortAdapters 87 }

-- SRP OC-12/STM-4 Single Mode Extended Reach Port Adapter for 7000 series

cevPaMcStm1Smi  OBJECT IDENTIFIER
    ::= { cevModuleVipPortAdapters 90 }

-- channelized STM-1 PA for 7500/7200(single mode intermediate reach)

cevPaMcStm1Mm  OBJECT IDENTIFIER
    ::= { cevModuleVipPortAdapters 91 }

-- channelized STM-1 PA for 7500/7200(multimode)

cevPa2feTxI82543  OBJECT IDENTIFIER
    ::= { cevModuleVipPortAdapters 92 }

-- 2 port Fast Ethernet 100TX Intel I82543

cevPa2feFxI82543  OBJECT IDENTIFIER
    ::= { cevModuleVipPortAdapters 93 }

-- 2 port Fast Ethernet 100FX (MMF) Intel I82543

cevPaDualWideGe  OBJECT IDENTIFIER
    ::= { cevModuleVipPortAdapters 94 }

-- Dual Wide Enhanced Gigabit Ethernet Port Adapter

cevPaVxa1T1E124  OBJECT IDENTIFIER
    ::= { cevModuleVipPortAdapters 95 }

-- 1 port T1/E1 voice port adapter w/ 7 DSPs

cevPaVxa1T1E130  OBJECT IDENTIFIER
    ::= { cevModuleVipPortAdapters 96 }

-- 1 port T1/E1 voice port adapter w/ 8 DSPs

cevPaMcT1E1  OBJECT IDENTIFIER
    ::= { cevModuleVipPortAdapters 97 }

-- Multichannel T1/E1 (without TDM) Port Adapter

cevPaMcx8te1M  OBJECT IDENTIFIER
    ::= { cevModuleVipPortAdapters 99 }

-- 8 port, software configurable Multichannel T1/E1 SS7 with TDM Port Adapter

cevPa1ce3  OBJECT IDENTIFIER
    ::= { cevModuleVipPortAdapters 100 }

-- 1 port, Multichannel E1 Port Adapter

cevPa2OC3PosSw  OBJECT IDENTIFIER
    ::= { cevModuleVipPortAdapters 101 }

-- Dual Port OC-3c Packet Over Sonet(POS) Single Wide Adapter

cevPa2feFxIsl  OBJECT IDENTIFIER
    ::= { cevModuleVipPortAdapters 102 }

-- PA-2feisl-fx fast ethernet 2 port adapter card

cevPa4Dtr  OBJECT IDENTIFIER
    ::= { cevModuleVipPortAdapters 103 }

-- Four port dedicated tokenring adapter

cevPaVmHda8FxsDid  OBJECT IDENTIFIER
    ::= { cevModuleVipPortAdapters 104 }

-- High density analog voice/fax voice module with 8 FXS/DID

cevPa1OC3PosSw  OBJECT IDENTIFIER
    ::= { cevModuleVipPortAdapters 105 }

-- Single port OC-3c Packet over Sonet (POS) Single Wide Port Adapter Card

cevPaA6mmOc3  OBJECT IDENTIFIER
    ::= { cevModuleVipPortAdapters 106 }

-- ATM WAN OC3 MM Port Adapter.

cevPaA6SmiOc3  OBJECT IDENTIFIER
    ::= { cevModuleVipPortAdapters 107 }

-- ATM WAN OC3 SMI Port Adapter.

cevPaA6SmlOc3  OBJECT IDENTIFIER
    ::= { cevModuleVipPortAdapters 108 }

-- ATM WAN OC3 SML Port Adapter.

cevPaA6Ds3  OBJECT IDENTIFIER
    ::= { cevModuleVipPortAdapters 109 }

-- ATM WAN OC3 DS3 Port Adapter.

cevPaA6E3  OBJECT IDENTIFIER
    ::= { cevModuleVipPortAdapters 110 }

-- ATM WAN OC3 E3 Port Adapter.

cevPaMcx4te1Q  OBJECT IDENTIFIER
    ::= { cevModuleVipPortAdapters 111 }

-- 4 port, software configurable Multichannel T1/E1 SS7 Q.703A with TDM

cevPaMct3ec  OBJECT IDENTIFIER
    ::= { cevModuleVipPortAdapters 112 }

-- Enhanced 1 port multichannel PA

cevPaMc2t3ec  OBJECT IDENTIFIER
    ::= { cevModuleVipPortAdapters 113 }

-- Enhanced 2 port multichannel PA

cevPa1t3e3ec  OBJECT IDENTIFIER
    ::= { cevModuleVipPortAdapters 114 }

-- Enhanced 1 port T3/E3  clear channel PA

cevPa2t3e3ec  OBJECT IDENTIFIER
    ::= { cevModuleVipPortAdapters 115 }

-- Enhanced 2 port T3/E3 clear channel PA

cevModuleCpuType  OBJECT IDENTIFIER
    ::= { cevModule 5 }

cevC7200Io1fe  OBJECT IDENTIFIER
    ::= { cevModuleCpuType 1 }

cevC7200Io  OBJECT IDENTIFIER
    ::= { cevModuleCpuType 2 }

cevCpuAS5300  OBJECT IDENTIFIER
    ::= { cevModuleCpuType 3 }

cevCpuRpm  OBJECT IDENTIFIER
    ::= { cevModuleCpuType 7 }

-- Router Processor Module

cevCpu2600  OBJECT IDENTIFIER
    ::= { cevModuleCpuType 8 }

-- c2600 chassis CPU

cevCpu7200Npe300  OBJECT IDENTIFIER
    ::= { cevModuleCpuType 9 }

-- Network processing engine (CPU card) for 7200 series

cevCpu1400  OBJECT IDENTIFIER
    ::= { cevModuleCpuType 10 }

-- CPU for Cisco 1400 series products

cevCpu800  OBJECT IDENTIFIER
    ::= { cevModuleCpuType 11 }

-- CPU for Cisco 800 series products

cevCpuPSM1Gbps  OBJECT IDENTIFIER
    ::= { cevModuleCpuType 12 }

-- Processor Switch Module with 1.2Gbps switching capacity for MGX8800 series chassis

cevCpu7200Npe175  OBJECT IDENTIFIER
    ::= { cevModuleCpuType 14 }

-- Network processing engine (CPU card) for 7200 series

cevCpu7200Npe225  OBJECT IDENTIFIER
    ::= { cevModuleCpuType 15 }

-- Network processing engine (CPU card) for 7200 series

cevCpu1417  OBJECT IDENTIFIER
    ::= { cevModuleCpuType 17 }

-- CPU for Cisco 1417 only

cevCpuPsm11oc12  OBJECT IDENTIFIER
    ::= { cevModuleCpuType 18 }

-- Cisco MGX8800 Processor Switch Module 1 with 1 622Mbps port

cevCpuOpticalRegenerator  OBJECT IDENTIFIER
    ::= { cevModuleCpuType 19 }

-- Cisco Optical Regenerator chassis CPU

cevCpuUbr924  OBJECT IDENTIFIER
    ::= { cevModuleCpuType 20 }

-- CPU for the UBR924 Cisco Cable Modem

cevCpu7120  OBJECT IDENTIFIER
    ::= { cevModuleCpuType 21 }

-- CPU for the 7120 series

cevCpu7140  OBJECT IDENTIFIER
    ::= { cevModuleCpuType 22 }

-- CPU for the 7140 series

cevCpuPsm12t3e3  OBJECT IDENTIFIER
    ::= { cevModuleCpuType 23 }

-- Cisco MGX8800 Processor Switch Module 1 with 2 T3/E3 ports

cevCpuPsm14oc3  OBJECT IDENTIFIER
    ::= { cevModuleCpuType 24 }

-- Cisco MGX8800 Processor Switch Module 1 with 4 155Mbps ports

cevCpu7200Npe100  OBJECT IDENTIFIER
    ::= { cevModuleCpuType 26 }

-- Network processing engine (CPU card) for 7200 series

cevCpu7200Npe150  OBJECT IDENTIFIER
    ::= { cevModuleCpuType 27 }

-- Network processing engine (CPU card) for 7200 series

cevCpu7200Npe200  OBJECT IDENTIFIER
    ::= { cevModuleCpuType 28 }

-- Network processing engine (CPU card) for 7200 series

cevCpuCreRp  OBJECT IDENTIFIER
    ::= { cevModuleCpuType 29 }

-- Central Routing Engine - Route Processor for Cisco 10000 series

cevCpuCreFp  OBJECT IDENTIFIER
    ::= { cevModuleCpuType 30 }

-- Central Routing Engine - Forwarding Processor for Cisco 10000 series

cevCpuAs5400  OBJECT IDENTIFIER
    ::= { cevModuleCpuType 31 }

-- CPU card for AS5400

cevCpuAS5200  OBJECT IDENTIFIER
    ::= { cevModuleCpuType 34 }

cevCpuGrp  OBJECT IDENTIFIER
    ::= { cevModuleCpuType 35 }

-- GSR Route Processor for 12012 and 12008

cevCpuMc3810V3  OBJECT IDENTIFIER
    ::= { cevModuleCpuType 36 }

-- CPU card for the MC3810-V3; higher performance than MC3810 with NEBs compliant changes.

cevCpuAs5850  OBJECT IDENTIFIER
    ::= { cevModuleCpuType 38 }

-- High End Dial Access Platform

cevCpu7200Npe400  OBJECT IDENTIFIER
    ::= { cevModuleCpuType 39 }

-- Network processing engine (CPU card) for 7200 series

cevCpuAs5350  OBJECT IDENTIFIER
    ::= { cevModuleCpuType 40 }

-- CPU card for AS5350

cevCpuRsp4Plus  OBJECT IDENTIFIER
    ::= { cevModuleCpuType 41 }

-- RSP4+ is ECC capable RSP4, ie.  With a Tiger5 asic

cevCpuUbr91x  OBJECT IDENTIFIER
    ::= { cevModuleCpuType 42 }

-- CPU card for the UBR91X family of Cable Modems (912-c, 912-s, 914)

cevCpu7150  OBJECT IDENTIFIER
    ::= { cevModuleCpuType 43 }

-- CPU for the 7150 series

cevCpuPXMB45Gbps  OBJECT IDENTIFIER
    ::= { cevModuleCpuType 44 }

-- PXM45B Processor Module with R7K Processor

cevCpuONS15540  OBJECT IDENTIFIER
    ::= { cevModuleCpuType 47 }

-- ONS 15540 ESP Processor Board without Switch Fabric

cevCpuRsp16  OBJECT IDENTIFIER
    ::= { cevModuleCpuType 48 }

-- RSP16 board processor

cevCpuPrp1  OBJECT IDENTIFIER
    ::= { cevModuleCpuType 49 }

-- GSR Performance Route Processor 1

cevCpuC7300Nse100  OBJECT IDENTIFIER
    ::= { cevModuleCpuType 50 }

-- Network Service Engine 100 (CPU card) for Cisco 7300 platform

cevCpuPXM1E1Gbps  OBJECT IDENTIFIER
    ::= { cevModuleCpuType 51 }

-- Cisco MGX88XX Processor Switch Module 1 Enhancement version

cevCpuPXM1E2Oc12  OBJECT IDENTIFIER
    ::= { cevModuleCpuType 52 }

-- Cisco MGX88XX Processor Switch Module 1, 2 OC12 ports, Enhanced version with PNNI support

cevCpuPXM1E8Oc3  OBJECT IDENTIFIER
    ::= { cevModuleCpuType 53 }

-- Cisco MGX88XX Processor Switch Module 1 Enhancement version with PNNI support

cevCpuPXM1E8T3E3  OBJECT IDENTIFIER
    ::= { cevModuleCpuType 54 }

-- Cisco MGX88XX Processor Switch Module 1 Enhanced version with 8 T3/E3 ports

cevCpuPXM1EComboT3E3Oc3  OBJECT IDENTIFIER
    ::= { cevModuleCpuType 55 }

-- Cisco MGX88XX Processor Switch Module 1 Enhancement version combo card with 8 T3/E3 and 4 OC3 ports

cevCpu7200Npeg1  OBJECT IDENTIFIER
    ::= { cevModuleCpuType 56 }

-- Network Processing Engine (CPU card) for 7200VXR series

cevCpu26912fe  OBJECT IDENTIFIER
    ::= { cevModuleCpuType 57 }

-- c2691 Motherboard with Fast Ethernet

cevCpu37452fe  OBJECT IDENTIFIER
    ::= { cevModuleCpuType 58 }

-- c3745 Motherboard with Fast Ethernet

cevCpu37252fe  OBJECT IDENTIFIER
    ::= { cevModuleCpuType 59 }

-- c3725 Motherboard with Fast Ethernet

cevCpu36311fe  OBJECT IDENTIFIER
    ::= { cevModuleCpuType 60 }

-- c3631 Motherboard with Fast Ethernet

cevCpu19002fe  OBJECT IDENTIFIER
    ::= { cevModuleCpuType 61 }

-- MWR 1900 Motherboard with Fast Ethernet

cevCpuONS15530SW  OBJECT IDENTIFIER
    ::= { cevModuleCpuType 62 }

-- Cisco ONS 15530 CPU and Switch Board

cevCpu6400Nsp  OBJECT IDENTIFIER
    ::= { cevModuleCpuType 63 }

-- Cisco 6400 Node Switch Processor

cevCpu6400Nrp  OBJECT IDENTIFIER
    ::= { cevModuleCpuType 64 }

-- Cisco 6400 Node Route Processor

cevCpu6400Nrp2  OBJECT IDENTIFIER
    ::= { cevModuleCpuType 65 }

-- Cisco 6400 Node Route Processor 2

cevCpu6400Nrp2Sv  OBJECT IDENTIFIER
    ::= { cevModuleCpuType 66 }

-- Cisco 6400 Node Route Processor 2 with Shaped VCs

cevCpuPXM1E4Oc3  OBJECT IDENTIFIER
    ::= { cevModuleCpuType 67 }

-- PXM1E-4-155 Cisco MGX88XX Processor Switch Module 1 Enhanced version with 4 OC3 ports

cevCpu1700  OBJECT IDENTIFIER
    ::= { cevModuleCpuType 68 }

-- CPU for the 1700 series

cevCpu7301Npeg1  OBJECT IDENTIFIER
    ::= { cevModuleCpuType 71 }

-- Cisco 7301 Network Processing Engine

cevCpuPXM1E16t1e1  OBJECT IDENTIFIER
    ::= { cevModuleCpuType 72 }

-- PXM1E-16-T1E1 processor card supports 16 port T1E1 IMA(Inverse Multplexing for ATM)

cevCpu7300Nse100Plus  OBJECT IDENTIFIER
    ::= { cevModuleCpuType 73 }

-- Network Service Engine 100+ for Cisco 7300 platform

cevCpuPxm1eB8t3e34Oc3  OBJECT IDENTIFIER
    ::= { cevModuleCpuType 74 }

-- PXM1E-T3E3-155/B  Cisco MGX88XX Processor Switch Module 1 Enhancement version combo card with 8 T3/E3 and 4 OC3 ports, Model B

cevCpu4604  OBJECT IDENTIFIER
    ::= { cevModuleCpuType 75 }

-- CPU card for catalyst 4000 Access Gateway line card

cevCpu4224  OBJECT IDENTIFIER
    ::= { cevModuleCpuType 76 }

-- CPU card for standalone 24 port ethernet switch, router and voice gateway

cevCpuAs5400HPX  OBJECT IDENTIFIER
    ::= { cevModuleCpuType 77 }

-- CPU card for AS5400HPX

cevCpuAs5350HPX  OBJECT IDENTIFIER
    ::= { cevModuleCpuType 78 }

-- CPU card for AS5350HPX

cevCpuAs5850tb  OBJECT IDENTIFIER
    ::= { cevModuleCpuType 80 }

-- BCM1250-based CPU card for AS5850 Route Switch Controller (RSC)

cevCpuC7300Npeg100  OBJECT IDENTIFIER
    ::= { cevModuleCpuType 81 }

-- Network Processing Engine (CPU card) for Cisco 7300 platform

cevCpuMdsCpp  OBJECT IDENTIFIER
    ::= { cevModuleCpuType 82 }

-- MDS platform Control Path processor

cevCpuMdsDpp  OBJECT IDENTIFIER
    ::= { cevModuleCpuType 83 }

-- MDS platform Data Path processor

cevCpuMdsSup  OBJECT IDENTIFIER
    ::= { cevModuleCpuType 84 }

-- MDS platform supervisor processor

cevCpu2430Iad24Fxs  OBJECT IDENTIFIER
    ::= { cevModuleCpuType 85 }

-- iad2430-24FXS Motherboard with 2FastEthernet, 24FXS ports

cevCpu2431Iad8Fxs  OBJECT IDENTIFIER
    ::= { cevModuleCpuType 86 }

-- iad2431-8FXS Motherboard with 1FastEthernet, 8FXS ports, 1T1/E1, 1 vwic slot

cevCpu2431Iad16Fxs  OBJECT IDENTIFIER
    ::= { cevModuleCpuType 87 }

-- iad2431-16FXS Motherboard with 2FastEthernet, 16FXS ports, 1T1/E1, 1 vwic slot

cevCpu2431Iad1T1E1  OBJECT IDENTIFIER
    ::= { cevModuleCpuType 88 }

-- iad2431-2T1E1 Motherboard with 2FastEthernet, 2T1/E1, 1 vwic slot

cevCpu2432Iad24Fxs  OBJECT IDENTIFIER
    ::= { cevModuleCpuType 89 }

-- iad2432-24FXS Motherboard with 2FastEthernet, 24FXS ports, 2T1/E1, 1 vwic slot

cevCpu3220  OBJECT IDENTIFIER
    ::= { cevModuleCpuType 90 }

-- Mobile Access Router Card(MARC) for 3220 Platform With 1 Fast Ethernet I/F

cevCpuVG224  OBJECT IDENTIFIER
    ::= { cevModuleCpuType 91 }

-- Line Side Analog Gateway with 24FXS Analog ports

cevCpuCat6kWsSup720RP  OBJECT IDENTIFIER
    ::= { cevModuleCpuType 92 }

-- Routing processor CPU for Catalyst 6000 WsSup720  supervisor

cevCpuCat6kMsfc  OBJECT IDENTIFIER
    ::= { cevModuleCpuType 93 }

-- CPU for Catalyst 6000 Msfc module

cevCpuCat6kMsfc2  OBJECT IDENTIFIER
    ::= { cevModuleCpuType 94 }

-- CPU for Catalyst 6000 Msfc2 module

cevCpuCat6kWsxSup12ge  OBJECT IDENTIFIER
    ::= { cevModuleCpuType 95 }

-- CPU for Catalyst 6000 WsxSup12ge supervisor

cevCpuCat6kWsxSup22ge  OBJECT IDENTIFIER
    ::= { cevModuleCpuType 96 }

-- CPU for Catalyst 6000 WsxSup22ge supervisor

cevCpuCat6kWsxSup1a2ge  OBJECT IDENTIFIER
    ::= { cevModuleCpuType 97 }

-- CPU for Catalyst 6000 WsxSup1a2ge supervisor

cevCpuCat6kWsSup720SP  OBJECT IDENTIFIER
    ::= { cevModuleCpuType 98 }

-- Switching processor CPU for Catalyst 6000 WsSup720 supervisor

cevCpu3845ge2  OBJECT IDENTIFIER
    ::= { cevModuleCpuType 99 }

-- c3845 Motherboard with Gigabit Ethernet

cevCpu3825ge2  OBJECT IDENTIFIER
    ::= { cevModuleCpuType 100 }

-- c3825 Motherboard with Gigabit Ethernet

cevCpuCrs1AsmpRoute  OBJECT IDENTIFIER
    ::= { cevModuleCpuType 101 }

-- CRS1 ASMP route processorr

cevCpuCrs1DsmpRoute  OBJECT IDENTIFIER
    ::= { cevModuleCpuType 102 }

-- CRS1 DSMP Distributed router processor.

cevCpuCrs1pfeAsic  OBJECT IDENTIFIER
    ::= { cevModuleCpuType 103 }

-- CRS1 Packet Forwarding Engine Asic module

cevCpuCrs1EgressqAsic  OBJECT IDENTIFIER
    ::= { cevModuleCpuType 104 }

-- CRS1 Egressq Asic module

cevCpuCrs1FabricqAsic  OBJECT IDENTIFIER
    ::= { cevModuleCpuType 105 }

-- CRS1 Fabricq Asic module

cevCpuCrs1IngressqAsic  OBJECT IDENTIFIER
    ::= { cevModuleCpuType 106 }

-- CRS1 Ingressq Asic module

cevCpuCrs1SPLC  OBJECT IDENTIFIER
    ::= { cevModuleCpuType 107 }

-- CRS1 Line card service processor.

cevCpuCrs1SPFC  OBJECT IDENTIFIER
    ::= { cevModuleCpuType 108 }

-- CRS1 Fabric card service processor

cevCpu1800Mod  OBJECT IDENTIFIER
    ::= { cevModuleCpuType 109 }

-- CPU type for 1800 series modular routers

cevCpuPrp2  OBJECT IDENTIFIER
    ::= { cevModuleCpuType 110 }

-- GSR Performance Route Processor 2

cevCpuCat6kWsSup32ge  OBJECT IDENTIFIER
    ::= { cevModuleCpuType 111 }

-- CPU for Catalyst 6500 WsSup328ge supervisor

cevCpuCat6kWsSup3210ge  OBJECT IDENTIFIER
    ::= { cevModuleCpuType 112 }

-- CPU for Catalyst 6500 WsSup3210ge supervisor

cevCpuAs5400XM  OBJECT IDENTIFIER
    ::= { cevModuleCpuType 113 }

-- CPU card for AS5400XM

cevCpuAs5350XM  OBJECT IDENTIFIER
    ::= { cevModuleCpuType 114 }

-- CPU card for AS5350XM

cevCpu1800  OBJECT IDENTIFIER
    ::= { cevModuleCpuType 115 }

-- CPU for the 1800 fixed-configuration series.

cevCpu7200Npeg2  OBJECT IDENTIFIER
    ::= { cevModuleCpuType 118 }

-- Network Processing Engine 2 (CPU card) for 7200VXR series

cevCpuCat6kMsfc2a  OBJECT IDENTIFIER
    ::= { cevModuleCpuType 119 }

-- CPU for Catalyst 6000 Msfc2A module

cevCpuC28012fe  OBJECT IDENTIFIER
    ::= { cevModuleCpuType 120 }

-- 2801 Motherboard with two integrated fast ethernets

cevCpuIXP2350WestportNP  OBJECT IDENTIFIER
    ::= { cevModuleCpuType 121 }

-- Processor used for Paldron development platform

cevCpuC7300Nse150  OBJECT IDENTIFIER
    ::= { cevModuleCpuType 122 }

-- Network Services Engine (CPU card) for the Cisco 7304 Platform

cevCpuCre1Rp  OBJECT IDENTIFIER
    ::= { cevModuleCpuType 123 }

-- Central Routing Engine 1 - Route Processor for Cisco 10000 series

cevCpuCre2Rp  OBJECT IDENTIFIER
    ::= { cevModuleCpuType 124 }

-- Central Routing Engine 2 - Route Processor for Cisco 10000 series

cevCpuCre3Rp  OBJECT IDENTIFIER
    ::= { cevModuleCpuType 125 }

-- Central Routing Engine 3 - Route Processor for Cisco 10000 series

cevCpuCre1Fp  OBJECT IDENTIFIER
    ::= { cevModuleCpuType 126 }

-- Central Routing Engine 1 - Forwarding Processor for Cisco 10000 series

cevCpuCre2Fp  OBJECT IDENTIFIER
    ::= { cevModuleCpuType 127 }

-- Central Routing Engine 2 - Forwarding Processor for Cisco 10000 series

cevCpuCre3Fp  OBJECT IDENTIFIER
    ::= { cevModuleCpuType 128 }

-- Central Routing Engine 3 - Forwarding Processor for Cisco 10000 series

cevCpu7600Sip600DC  OBJECT IDENTIFIER
    ::= { cevModuleCpuType 130 }

-- CPU for 7600 SIP 600 DC module

cevCpuCat6kVsF6kMsfc3  OBJECT IDENTIFIER
    ::= { cevModuleCpuType 131 }

-- CPU for Catalyst 6500 Supervisor VS-F6K-MSFC3 Module

cevCpuCat6kVsS72010G  OBJECT IDENTIFIER
    ::= { cevModuleCpuType 132 }

-- CPU for Catalyst 6500 Supervisor VS-S720-10G Module

cevCpu7201Npeg2  OBJECT IDENTIFIER
    ::= { cevModuleCpuType 133 }

-- Network Processing Engine 2 (CPU card) for 7201 series

cevCpuSamiDc8548H  OBJECT IDENTIFIER
    ::= { cevModuleCpuType 134 }

-- CPU on the daughter cards on Service and Application Module for IP

cevCpuUC500  OBJECT IDENTIFIER
    ::= { cevModuleCpuType 135 }

-- Processor

cevCpuBroadcomSB1A  OBJECT IDENTIFIER
    ::= { cevModuleCpuType 138 }

-- Broadcom SB-1A high performance MIPS64 CPU

cevCpuCrs1SPLCB  OBJECT IDENTIFIER
    ::= { cevModuleCpuType 139 }

-- Cisco CRS-1 Modular Services Card Rev B

cevCpuUc520s  OBJECT IDENTIFIER
    ::= { cevModuleCpuType 140 }

-- CPU card for the UC520 UCSO fixed-configuration series

cevCpuUc520m  OBJECT IDENTIFIER
    ::= { cevModuleCpuType 141 }

-- CPU card for the 19 inch rack-mount model of UC520 series

cevCpu1861  OBJECT IDENTIFIER
    ::= { cevModuleCpuType 144 }

-- Cpu card for the ISR flavour of freddo

cevCpuTraffic  OBJECT IDENTIFIER
    ::= { cevModuleCpuType 145 }

-- NME-APA SCE Entity Traffic Processor

cevCpuCat6kWsSup32Pge  OBJECT IDENTIFIER
    ::= { cevModuleCpuType 146 }

-- CPU for Catalyst 6500 WsSup32Pge supervisor

cevCpuCat6kWsSup32P10ge  OBJECT IDENTIFIER
    ::= { cevModuleCpuType 147 }

-- CPU for Catalyst 6500 WsSup32P10ge supervisor

cevCpuCat6kWsF6kPisa  OBJECT IDENTIFIER
    ::= { cevModuleCpuType 148 }

-- CPU for Catalyst 6500 PISA router daughterboard

cevCpuCrs1PlimAsic  OBJECT IDENTIFIER
    ::= { cevModuleCpuType 152 }

-- CRS1 PLIM Asic module

cevCpu2435Iad8Fxs  OBJECT IDENTIFIER
    ::= { cevModuleCpuType 153 }

-- iad2431-8FXS Motherboard with 2FastEthernet,8FXS ports and 1T1/E1

cevCpuVG204  OBJECT IDENTIFIER
    ::= { cevModuleCpuType 154 }

-- Line Side Analog Gateway with 4FXS Analog ports

cevCpuVG202  OBJECT IDENTIFIER
    ::= { cevModuleCpuType 155 }

-- Line Side Analog Gateway with 2FXS Analog ports

cevCpu2941  OBJECT IDENTIFIER
    ::= { cevModuleCpuType 157 }

-- CPU for MWR-2941-DC

cevCPU8641D  OBJECT IDENTIFIER
    ::= { cevModuleCpuType 158 }

-- Cisco ASR9K RSP, LC CPU Type

cevCpuCat6kVsSup2t10g  OBJECT IDENTIFIER
    ::= { cevModuleCpuType 159 }

-- CPU for Catalyst 6500 Supervisor Module VS-SUP2T-10G

cevCpu19412ge  OBJECT IDENTIFIER
    ::= { cevModuleCpuType 160 }

-- Cisco 1941 Motherboard with 2 GE

cevCpu29012ge  OBJECT IDENTIFIER
    ::= { cevModuleCpuType 161 }

-- Cisco 2901 Motherboard with 2 GE

cevCpu29113ge  OBJECT IDENTIFIER
    ::= { cevModuleCpuType 162 }

-- Cisco 2911 Motherboard with 3 GE

cevCpu29213ge  OBJECT IDENTIFIER
    ::= { cevModuleCpuType 163 }

-- Cisco 2921 Motherboard with 3 GE

cevCpu29513ge  OBJECT IDENTIFIER
    ::= { cevModuleCpuType 164 }

-- Cisco 2951 Motherboard with 3 GE

cevCpu39253ge  OBJECT IDENTIFIER
    ::= { cevModuleCpuType 165 }

-- Cisco 3925 w/SPE100 with 3 GE

cevCpu39453ge  OBJECT IDENTIFIER
    ::= { cevModuleCpuType 166 }

-- Cisco 3945 w/SPE150 with 3 GE

cevCpuSr520T1  OBJECT IDENTIFIER
    ::= { cevModuleCpuType 167 }

-- This is the security router with 1 port T1. Supports Voice and data

cevCpu1941w2ge  OBJECT IDENTIFIER
    ::= { cevModuleCpuType 168 }

-- Cisco 1941 Motherboard with 2 GE,  802.11n WLAN

cevCpu3825nvge2  OBJECT IDENTIFIER
    ::= { cevModuleCpuType 169 }

-- c3825nv Motherboard with Gigabit Ethernet

cevCpu3845nvge2  OBJECT IDENTIFIER
    ::= { cevModuleCpuType 170 }

-- c3845nv Motherboard with Gigabit Ethernet

cevCpuCrs1SPFP  OBJECT IDENTIFIER
    ::= { cevModuleCpuType 175 }

-- Cisco CRS-1 Series Forwarding Processor 40G

cevCpu3900SPE2004ge  OBJECT IDENTIFIER
    ::= { cevModuleCpuType 179 }

-- cisco 3900 Services Performance Engine 200 (SPE200) with 4 GE, 3 EHWIC, 3 DSP

cevCpu3900Spe100K9  OBJECT IDENTIFIER
    ::= { cevModuleCpuType 182 }

-- Cisco Services Performance Engine 100 for Cisco 3900 ISR with three Gigabit Ethernet

cevCpu3900Spe150K9  OBJECT IDENTIFIER
    ::= { cevModuleCpuType 183 }

-- Cisco Services Performance Engine 150 for Cisco 3900 ISR with three Gigabit Ethernet

cevCpu3900SPE2504ge  OBJECT IDENTIFIER
    ::= { cevModuleCpuType 186 }

-- cisco 3900 Services Performance Engine 250 (SPE250) with 4 GE, 3 EHWIC, 3 DSP

cevCpuCrs1FP140  OBJECT IDENTIFIER
    ::= { cevModuleCpuType 187 }

-- Cisco CRS Series Forwarding Processor 140G

cevCpuCrs1MSC140G  OBJECT IDENTIFIER
    ::= { cevModuleCpuType 188 }

-- Cisco CRS Series Modular Services Card 140G

cevCpuC1841C2fek9  OBJECT IDENTIFIER
    ::= { cevModuleCpuType 189 }

-- 1841C/K9 Motherboard with two integrated fast ethernets

cevCpuC2801C2fek9  OBJECT IDENTIFIER
    ::= { cevModuleCpuType 190 }

-- 2801C/K9 Motherboard  with two integrated fast ethernets

cevCpuC2811C2fek9  OBJECT IDENTIFIER
    ::= { cevModuleCpuType 191 }

-- 2811C/K9 Motherboard with two integrated fast ethernets and integrated VPN

cevCpuC2821C2gek9  OBJECT IDENTIFIER
    ::= { cevModuleCpuType 192 }

-- 2821C/K9 Motherboard with two integrated gigabit ethernets and integrated VPN

cevCpu3825C2gek9  OBJECT IDENTIFIER
    ::= { cevModuleCpuType 194 }

-- 3825C/K9 Motherboard with Gigabit Ethernet

cevCpu3845C2gek9  OBJECT IDENTIFIER
    ::= { cevModuleCpuType 195 }

-- 3845C/K9 Motherboard with Gigabit Ethernet

cevCpuCGR20102ge  OBJECT IDENTIFIER
    ::= { cevModuleCpuType 198 }

-- Cisco Connected Grid Router 2010 Motherboard with 2 GE

cevCpu1906Ck9  OBJECT IDENTIFIER
    ::= { cevModuleCpuType 199 }

-- 1906C/K9 Motherboard with 2 GE, Serial 1T for china

cevCpuDsp  OBJECT IDENTIFIER
    ::= { cevModuleCpuType 201 }

-- Generic Digital Signal Processor

cevCpu5915  OBJECT IDENTIFIER
    ::= { cevModuleCpuType 202 }

-- CPU for 5915 Embedded services router

cevCpu86xVAE  OBJECT IDENTIFIER
    ::= { cevModuleCpuType 212 }

-- CPU for Cisco 86xVAE series products

cevCpuCryptoAsic  OBJECT IDENTIFIER
    ::= { cevModuleCpuType 213 }

-- Generic Crypto Asic, which encrypt and decrypt packets

cevCpu2811ve2fe  OBJECT IDENTIFIER
    ::= { cevModuleCpuType 214 }

-- 2811ve Motherboard with two integrated fast ethernets and integrated VPN

cevCpu1841ve2fe  OBJECT IDENTIFIER
    ::= { cevModuleCpuType 215 }

-- 1841ve Motherboard with two integrated fast ethernets

cevCpu819HG  OBJECT IDENTIFIER
    ::= { cevModuleCpuType 216 }

-- C819HG Hardened Router series with 1 Gigabit Ethernet WAN, 4 Fast Ethernet LAN, 1 3G WAN, 1 Serial, 1 Console/Aux ports, 256MB flash memory, 512MB DRAM

cevCpu819G  OBJECT IDENTIFIER
    ::= { cevModuleCpuType 217 }

-- C819G Router  series with 1 Gigabit Ethernet WAN, 4 Fast Ethernet LAN, 1 3G WAN, 1 Serial, 1 Console/Aux ports, 256MB flash memory and 512MB DRAM

cevCpu881W  OBJECT IDENTIFIER
    ::= { cevModuleCpuType 218 }

-- C881W Router series with 1 Fast Ethernet WAN, 4 Fast Ethernet LAN with 2 PoE, Wireless LAN, 1 USB 2.0 port, 1 Console/Aux port, 256MB flash memory and 512MB DRAM

cevCpu886VAW  OBJECT IDENTIFIER
    ::= { cevModuleCpuType 219 }

-- C886VA-W Router series with 1 ADSL2/2+ Annex B, 1 ISDN,  4 Fast Ethernet LAN with 2 PoE, Wireless LAN, 1 USB 2.0 port, 1 Console/Aux port, 256MB flash memory and 512MB DRAM

cevCpu887VAMW  OBJECT IDENTIFIER
    ::= { cevModuleCpuType 220 }

-- C887VAM-W Router series with 1 ADSL2/2+ Annex M, 4 Fast Ethernet LAN with 2 PoE, Wireless LAN, 1 USB 2.0 port, 1 Console/Aux port, 256MB flash memory and 512MB DRAM

cevCpu887VAW  OBJECT IDENTIFIER
    ::= { cevModuleCpuType 221 }

-- C887VA-W Router series with 1 VDSL, 4 Fast Ethernet LAN with 2 PoE, Wireless LAN, 1 USB 2.0 port, 1 Console/Aux port, 256MB flash memory and 512MB DRAM

cevCpuAsaSm1  OBJECT IDENTIFIER
    ::= { cevModuleCpuType 222 }

-- Central Processing Unit for Cisco Adaptive Security Appliance for Catalyst switches

cevCpuAsaSm1K7  OBJECT IDENTIFIER
    ::= { cevModuleCpuType 223 }

-- Central Processing Unit for Cisco Adaptive Security Appliance with No Payload Encryption for Catalyst switches

cevCpuCrsLSP140  OBJECT IDENTIFIER
    ::= { cevModuleCpuType 234 }

-- Cisco CRS Series Label Switch Processor 140G

cevCpuCre5Fp  OBJECT IDENTIFIER
    ::= { cevModuleCpuType 243 }

-- Central Routing Engine 5 - Forwarding Processor for Cisco 10000 series

cevCpuCre5Rp  OBJECT IDENTIFIER
    ::= { cevModuleCpuType 244 }

-- Central Routing Engine 5 - Route Processor for Cisco 10000 series

cevCpu819HGW  OBJECT IDENTIFIER
    ::= { cevModuleCpuType 250 }

-- C819HGW Hardened Router series with 1 Gigabit Ethernet WAN, 4 Fast Ethernet LAN, 1 3G WAN, Wireless LAN, 1 Serial, 1 Console/Aux ports, 1GB flash memory, 1GB DRAM

cevCpu819H  OBJECT IDENTIFIER
    ::= { cevModuleCpuType 251 }

-- C819H Hardened Router series with 1 Gigabit Ethernet WAN, 4 Fast Ethernet LAN, 1 Serial, 1 Console/Aux ports, 1GB flash memory, 1GB DRAM

cevCpu819HWD  OBJECT IDENTIFIER
    ::= { cevModuleCpuType 252 }

-- C819HWD Hardened Router series with 1 Gigabit Ethernet WAN, 4 Fast Ethernet LAN, Wireless LAN, 1 Serial, 1 Console/Aux ports, 1GB flash memory, 1GB DRAM

cevCpu812G  OBJECT IDENTIFIER
    ::= { cevModuleCpuType 253 }

-- C812G Router series with 1 Gigabit Ethernet WAN, 1 3G WAN, 1 Console/Aux ports, 512MB flash memory, 512MB DRAM

cevCpu812GCIFI  OBJECT IDENTIFIER
    ::= { cevModuleCpuType 254 }

-- C812GCIFI Router series with 1 Gigabit Ethernet WAN, 1 3G WAN, Wireless LAN, 1 Console/Aux ports, 512MB flash memory, 512MB DRAM

cevCpu819HGM  OBJECT IDENTIFIER
    ::= { cevModuleCpuType 255 }

-- C819HGM Hardened Router series with 1 Gigabit Ethernet WAN, 4 Fast Ethernet LAN, 1 3G WAN, 1 Serial, 1 Console/Aux ports, 1GB flash memory, 1GB DRAM

cevCpu819GM  OBJECT IDENTIFIER
    ::= { cevModuleCpuType 256 }

-- C819GM Router  series with 1Gigabit Ethernet WAN, 4 Fast Ethernet LAN, 1 3G WAN, 1 Serial, 1 Console/Aux ports, 1GB flash memory, 1GB DRAM

cevCpuCgrSup  OBJECT IDENTIFIER
    ::= { cevModuleCpuType 266 }

-- Connected Grid Router - platform supervisor processor

cevCpu86xVAEW  OBJECT IDENTIFIER
    ::= { cevModuleCpuType 267 }

-- CPU for Cisco 86xVAEW series products

cevCpuvg202xm  OBJECT IDENTIFIER
    ::= { cevModuleCpuType 268 }

-- Line side Analog Gateway VG202XM with 2FXS Analog ports

cevCpuvg204xm  OBJECT IDENTIFIER
    ::= { cevModuleCpuType 269 }

-- Line side Analog Gateway VG204XM with 4FXS Analog ports

cevCpu1783SR  OBJECT IDENTIFIER
    ::= { cevModuleCpuType 280 }

-- CPU for C819H-K9 Hardened Router for Rockwell Automation with 1 Gigabit Ethernet WAN, 4 Fast Ethernet LAN, 1 Serial, 1 Console/Aux port, 256MB flash memory and 256MB DRAM

cevCPURT1081K9  OBJECT IDENTIFIER
    ::= { cevModuleCpuType 293 }

-- Router 1081 Fast Ethernet Router

cevCPURT1091K9  OBJECT IDENTIFIER
    ::= { cevModuleCpuType 294 }

-- Router 1091 GigaE SecRouter

cevCpuRT2241K9  OBJECT IDENTIFIER
    ::= { cevModuleCpuType 295 }

-- Router 2241 w/2 GE,2 EHWIC slots,256MB CF,512MB DRAM,IP Base

cevCpuRT2221K9  OBJECT IDENTIFIER
    ::= { cevModuleCpuType 296 }

-- Router 2221 Modular Router, 2 GE, 2 EHWIC slots, 512DRAM, IP Base

cevCpuRT2241WCK9  OBJECT IDENTIFIER
    ::= { cevModuleCpuType 297 }

-- Router 2241 Router w/802.11 a/b/g/n China Compliant WLAN ISM

cevCpuRT3211K9  OBJECT IDENTIFIER
    ::= { cevModuleCpuType 298 }

-- Router 3211 w/3 GE,4 EHWIC,2 DSP,1 SM,256MB CF,512MB DRAM,IPB

cevCpuRT3221K9  OBJECT IDENTIFIER
    ::= { cevModuleCpuType 299 }

-- Router 3221 w/3 GE,4 EHWIC,3 DSP,1 SM,256MB CF,512MB DRAM,IPB

cevCpuRT3201K9  OBJECT IDENTIFIER
    ::= { cevModuleCpuType 300 }

-- Router 3201 w/2 GE,4 EHWIC,2 DSP,256MB CF,512MB DRAM,IP Base

cevModuleCscType  OBJECT IDENTIFIER
    ::= { cevModule 6 }

cevModuleC7xxxType  OBJECT IDENTIFIER
    ::= { cevModule 7 }

cevC7xxxMc14a  OBJECT IDENTIFIER
    ::= { cevModuleC7xxxType 1 }

-- cable card 1 downstream 4 upstream

cevC7xxxMc16a  OBJECT IDENTIFIER
    ::= { cevModuleC7xxxType 2 }

-- cable card 1 downstream 6 upstream

cevC7xxxMc11  OBJECT IDENTIFIER
    ::= { cevModuleC7xxxType 3 }

-- cable card 1 downstream 1 upstream

cevC7xxxMc12a  OBJECT IDENTIFIER
    ::= { cevModuleC7xxxType 4 }

-- cable card 1 downstream 2 upstream

cevC7xxxMc11a  OBJECT IDENTIFIER
    ::= { cevModuleC7xxxType 5 }

-- modem card 1 downstream 1 upstream (ASIC)

cevC7xxxIo1feTxIsl  OBJECT IDENTIFIER
    ::= { cevModuleC7xxxType 6 }

-- Fast Ethernet I/O Controller which provides RJ45 and MII Connectors

cevC7xxxMc28  OBJECT IDENTIFIER
    ::= { cevModuleC7xxxType 8 }

-- cable card 2 downstream 8 upstream

cevVip480  OBJECT IDENTIFIER
    ::= { cevModuleC7xxxType 9 }

-- 4th Generation Versatile Interface Processor for the c7500 router

cevVip450  OBJECT IDENTIFIER
    ::= { cevModuleC7xxxType 10 }

-- 4th Generation Versatile Interface Processor for the c7500 router, lower performance than cevVip480 card

cevC7xxxIoEGE  OBJECT IDENTIFIER
    ::= { cevModuleC7xxxType 11 }

-- C7200 I/O Controller with GE(1000Mbps) + E(10Mbps) interface

cevC7xxxIo2FE  OBJECT IDENTIFIER
    ::= { cevModuleC7xxxType 12 }

-- C7200 I/O Controller with 2FE (10/100Mbps) interface

cevC7xxxEIP  OBJECT IDENTIFIER
    ::= { cevModuleC7xxxType 16 }

-- Ethernet Interface Processor

cevC7xxxFIP  OBJECT IDENTIFIER
    ::= { cevModuleC7xxxType 17 }

-- FDDI Interface Processor

cevC7xxxSrsFIP  OBJECT IDENTIFIER
    ::= { cevModuleC7xxxType 18 }

-- FDDI Interface Processor

cevC7xxxTRIP  OBJECT IDENTIFIER
    ::= { cevModuleC7xxxType 19 }

-- Token Ring Interface Processor

cevC7xxxSrsTRIP  OBJECT IDENTIFIER
    ::= { cevModuleC7xxxType 20 }

-- Token Ring Interface Processor

cevC7xxxFSIP  OBJECT IDENTIFIER
    ::= { cevModuleC7xxxType 21 }

-- Fast Serial Interface Processor

cevC7xxxSSIP  OBJECT IDENTIFIER
    ::= { cevModuleC7xxxType 22 }

-- Standard Serial Interface Processor

cevC7xxxMIP  OBJECT IDENTIFIER
    ::= { cevModuleC7xxxType 23 }

-- Multichannel Interface Processor

cevC7xxxSMIP  OBJECT IDENTIFIER
    ::= { cevModuleC7xxxType 24 }

-- ISP Multichannel Interface Processor

cevC7xxxVIP2  OBJECT IDENTIFIER
    ::= { cevModuleC7xxxType 25 }

-- Versatile Interface Processor 2

cevC7xxxVIP250  OBJECT IDENTIFIER
    ::= { cevModuleC7xxxType 26 }

-- Versatile Interface Processor 2-50

cevC7xxxRSP1  OBJECT IDENTIFIER
    ::= { cevModuleC7xxxType 27 }

-- Route Switch Processor 1

cevC7xxxRSP2  OBJECT IDENTIFIER
    ::= { cevModuleC7xxxType 28 }

-- Route Switch Processor 2

cevC7xxxRSP4  OBJECT IDENTIFIER
    ::= { cevModuleC7xxxType 29 }

-- Route Switch Processor 4

cevC7xxxPosIP  OBJECT IDENTIFIER
    ::= { cevModuleC7xxxType 30 }

-- Packet Over Sonet Interface Processor

cevC7xxxFeIP2  OBJECT IDENTIFIER
    ::= { cevModuleC7xxxType 31 }

-- Fast Ethernet Interface Processor 2

cevC73004Oc3PosMm  OBJECT IDENTIFIER
    ::= { cevModuleC7xxxType 33 }

-- 4-port OC3 POS line card for Cisco 7300, Multimode

cevC73004Oc3PosSmIr  OBJECT IDENTIFIER
    ::= { cevModuleC7xxxType 34 }

-- 4-port OC3 POS line card for Cisco 7300, Singlemode, Intermediate Reach

cevC73004Oc3PosSmLr  OBJECT IDENTIFIER
    ::= { cevModuleC7xxxType 35 }

-- 4-port OC3 POS line card for Cisco 7300, Singlemode, Long Reach

cevC7300Oc48PosSmSr  OBJECT IDENTIFIER
    ::= { cevModuleC7xxxType 36 }

-- 1-port OC48 POS line card for Cisco 7300, Singlemode, Short Reach

cevC7300Oc48PosSmIr  OBJECT IDENTIFIER
    ::= { cevModuleC7xxxType 37 }

-- 1-port OC48 POS line card for Cisco 7300, Singlemode, Intermediate Reach

cevC7300Oc48PosSmLr  OBJECT IDENTIFIER
    ::= { cevModuleC7xxxType 38 }

-- 1-port OC48 POS line card for Cisco 7300, Singlemode, Long Reach

cevC7500AIP  OBJECT IDENTIFIER
    ::= { cevModuleC7xxxType 58 }

-- ATM Interface Processor for 7500 Platform

cevC7500CIP  OBJECT IDENTIFIER
    ::= { cevModuleC7xxxType 59 }

-- Channel Interface Processor for 7500 Platform

cevC7500CIP2  OBJECT IDENTIFIER
    ::= { cevModuleC7xxxType 60 }

-- Channel Interface Processor 2 for 7500 Platform

cevC7500GEIP  OBJECT IDENTIFIER
    ::= { cevModuleC7xxxType 61 }

-- Gigabit Ethernet Interface Processor for 7500 Platform

cevC7500FEIP  OBJECT IDENTIFIER
    ::= { cevModuleC7xxxType 62 }

-- Fast Ethernet Interface Processor for 7500 Platform

cevC7xxxSIP  OBJECT IDENTIFIER
    ::= { cevModuleC7xxxType 63 }

-- Serial Interface Processor

cevC7xxxRSP  OBJECT IDENTIFIER
    ::= { cevModuleC7xxxType 64 }

-- Route Switch Processor for 7000 Platforms

cevC7xxxHSSI  OBJECT IDENTIFIER
    ::= { cevModuleC7xxxType 65 }

-- High Speed Serial Interface

cevC7411  OBJECT IDENTIFIER
    ::= { cevModuleC7xxxType 66 }

-- Cisco 7400 Family, 1 Slot Router

cevC7411IoGE  OBJECT IDENTIFIER
    ::= { cevModuleC7xxxType 67 }

-- Cisco 7411 I/O Controller with three 10/100/1000Mbps GE interfaces

cevC7301  OBJECT IDENTIFIER
    ::= { cevModuleC7xxxType 68 }

-- Cisco 7300 Family, 1 sLOT rOUTER

cevC7301IoGE  OBJECT IDENTIFIER
    ::= { cevModuleC7xxxType 69 }

-- Cisco 7301 I/O Controller with three 10/100/1000Mbps GE interfaces

cevVip680  OBJECT IDENTIFIER
    ::= { cevModuleC7xxxType 70 }

-- A new VIP card to be used in 7500 box. this card is same as VIP4-80 but with a higher speed CPU.

cevC7300CCPA  OBJECT IDENTIFIER
    ::= { cevModuleC7xxxType 76 }

-- Port Adaptor Carrier Card for Cisco 7304

cevC7304MSC100  OBJECT IDENTIFIER
    ::= { cevModuleC7xxxType 77 }

-- C7304-MSC-100 is a carrier card for 7304. it can carry up to 2 VPA (Versatile Port Adaptor) cards

cevC73006E3  OBJECT IDENTIFIER
    ::= { cevModuleC7xxxType 78 }

-- 6-port E3 interface line card for Cisco 7300

cevC73001Oc12Atm  OBJECT IDENTIFIER
    ::= { cevModuleC7xxxType 79 }

-- 1-port OC12 ATM line card for Cisco 7300

cevC7200Vsa  OBJECT IDENTIFIER
    ::= { cevModuleC7xxxType 81 }

-- C7200 VPN Services Adapter

cevModuleC4xxxType  OBJECT IDENTIFIER
    ::= { cevModule 8 }

cevC4xxxUnknown  OBJECT IDENTIFIER
    ::= { cevModuleC4xxxType 1 }

cevC4xxxNp4Gb  OBJECT IDENTIFIER
    ::= { cevModuleC4xxxType 2 }

-- 4-Port Serial E1/G.703

cevC4wsx4548GbRj45VPlus  OBJECT IDENTIFIER
    ::= { cevModuleC4xxxType 3 }

-- Catalyst 4500 series 48-port 10/100/1000BaseT linecard with Power Over Ethernet, upto 30W inline power per port

cevCat4kWsx4948e10GE  OBJECT IDENTIFIER
    ::= { cevModuleC4xxxType 4 }

-- Catalyst 4000 series fixed configuration switch with 48 10/100/1000BaseT ports and four 10Gbps/1Gbps SFP+/SFP ports(WS-C4948E)

cevCat4kWsx45Sup7LE  OBJECT IDENTIFIER
    ::= { cevModuleC4xxxType 5 }

-- First Cat4K supervisor based on IFE chipset

cevCat4kWsx45Sup8e  OBJECT IDENTIFIER
    ::= { cevModuleC4xxxType 6 }

-- Catalyst 4500 Sup 8-E Wired Wireless Convergence, 928 Gbps Wired, 8x10Gbps SFP+ uplink ports

cevModuleAS5200Type  OBJECT IDENTIFIER
    ::= { cevModule 9 }

cevAS5200Carrier  OBJECT IDENTIFIER
    ::= { cevModuleAS5200Type 1 }

-- Microcom and V.110 carrier card

cevAS5200DtdCarrier  OBJECT IDENTIFIER
    ::= { cevModuleAS5200Type 2 }

-- Mica carrier card

cevPmAS5xxx12m56k  OBJECT IDENTIFIER
    ::= { cevModuleAS5200Type 3 }

-- Microcom 12-port modem module

cevPmAS5xxx12mV110  OBJECT IDENTIFIER
    ::= { cevModuleAS5200Type 4 }

-- V.110 terminal adapter 12-port module

cevModuleC25xxType  OBJECT IDENTIFIER
    ::= { cevModule 10 }

cevModuleAS5300Type  OBJECT IDENTIFIER
    ::= { cevModule 11 }

cevAS53004ct1  OBJECT IDENTIFIER
    ::= { cevModuleAS5300Type 1 }

cevAS53004ce1  OBJECT IDENTIFIER
    ::= { cevModuleAS5300Type 2 }

cevPmDtdCarrier  OBJECT IDENTIFIER
    ::= { cevModuleAS5300Type 3 }

cevPmDtd6m  OBJECT IDENTIFIER
    ::= { cevModuleAS5300Type 4 }

cevAS5300Carrier  OBJECT IDENTIFIER
    ::= { cevModuleAS5300Type 5 }

cevPmAS5xxx12m  OBJECT IDENTIFIER
    ::= { cevModuleAS5300Type 6 }

cevAS5300VoiceCarrierCard  OBJECT IDENTIFIER
    ::= { cevModuleAS5300Type 7 }

cevAS5300Dspmc542  OBJECT IDENTIFIER
    ::= { cevModuleAS5300Type 8 }

-- DSP (Digital Signal Processor) C542 module for the AS5300 and AS5800 series

cevAS5300Dsp  OBJECT IDENTIFIER
    ::= { cevModuleAS5300Type 9 }

cevAS5300PmDtd12m  OBJECT IDENTIFIER
    ::= { cevModuleAS5300Type 10 }

-- Mica 12 modem module

cevAS53008ct14t  OBJECT IDENTIFIER
    ::= { cevModuleAS5300Type 11 }

-- Channelized Octal T1 and 4 serial card

cevAS53008ce14t  OBJECT IDENTIFIER
    ::= { cevModuleAS5300Type 12 }

-- Channelized Octal E1 and 4 serial card

cevAS53004ct14t  OBJECT IDENTIFIER
    ::= { cevModuleAS5300Type 13 }

-- Channelized Quad T1 and 4 serial card

cevAS53004ce14t  OBJECT IDENTIFIER
    ::= { cevModuleAS5300Type 14 }

-- Channelized Quad E1 and 4 serial card

cevAS5300Amazon2Carrier  OBJECT IDENTIFIER
    ::= { cevModuleAS5300Type 15 }

-- Amazon II mica carrier card

cevAS5300Dspm6c549  OBJECT IDENTIFIER
    ::= { cevModuleAS5300Type 16 }

-- DSP (Digital Signal Processor) module that contains 6 C549 DSPs, used in AS5300 and AS5800

cevModuleAS5800Type  OBJECT IDENTIFIER
    ::= { cevModule 12 }

cevMAs5800Dsc  OBJECT IDENTIFIER
    ::= { cevModuleAS5800Type 1 }

cevMAs5800E1  OBJECT IDENTIFIER
    ::= { cevModuleAS5800Type 2 }

cevMAs5800T1  OBJECT IDENTIFIER
    ::= { cevModuleAS5800Type 3 }

cevMAs5800MicaHmm  OBJECT IDENTIFIER
    ::= { cevModuleAS5800Type 4 }

cevMAs5800T3  OBJECT IDENTIFIER
    ::= { cevModuleAS5800Type 5 }

-- T3 Trunk Card

cevMAs5800FeDsi  OBJECT IDENTIFIER
    ::= { cevModuleAS5800Type 6 }

cevMAs5800MicaDmm  OBJECT IDENTIFIER
    ::= { cevModuleAS5800Type 7 }

-- Mica Double Density Modem Module

cevMAs5800Vcc  OBJECT IDENTIFIER
    ::= { cevModuleAS5800Type 8 }

-- Voice Carrier Card

cevMAs5800Dspm6c549  OBJECT IDENTIFIER
    ::= { cevModuleAS5800Type 9 }

-- Digital Signal Processor Module with 6 C549's Voice Feature Card

cevMAs5800Dsp  OBJECT IDENTIFIER
    ::= { cevModuleAS5800Type 10 }

-- Digital Signal Processor Module Voice Feature Card

cevModuleFabricType  OBJECT IDENTIFIER
    ::= { cevModule 14 }

cev12012Sfc  OBJECT IDENTIFIER
    ::= { cevModuleFabricType 3 }

-- 12012 Switch Fabric Card

cev12012Csc  OBJECT IDENTIFIER
    ::= { cevModuleFabricType 4 }

-- 12012 Clock Scheduler Card

cev12008Sfc8  OBJECT IDENTIFIER
    ::= { cevModuleFabricType 5 }

-- 12008 Switch Fabric Card

cev12008Csc8  OBJECT IDENTIFIER
    ::= { cevModuleFabricType 6 }

-- 12008 Clock Scheduler Card

cev12016Sfc16  OBJECT IDENTIFIER
    ::= { cevModuleFabricType 7 }

-- GSR 12016 Switch Fabric Card

cev12016Csc16  OBJECT IDENTIFIER
    ::= { cevModuleFabricType 8 }

-- GSR 12016 Clock Scheduler Card

cev12016Sfc16Oc192  OBJECT IDENTIFIER
    ::= { cevModuleFabricType 9 }

-- GSR 12016 OC192 Switch Fabric Card

cev12016Csc16Oc192  OBJECT IDENTIFIER
    ::= { cevModuleFabricType 10 }

-- GSR 12016 OC192 Clock Scheduler Card

cev12010Sfc10  OBJECT IDENTIFIER
    ::= { cevModuleFabricType 11 }

-- GSR 12010 Switch Fabric Card

cev12010Csc10  OBJECT IDENTIFIER
    ::= { cevModuleFabricType 12 }

-- GSR 12010 Clock Scheduler Card

cev12406Sfc6  OBJECT IDENTIFIER
    ::= { cevModuleFabricType 13 }

-- GSR 12406 Switch Fabric Card

cev12406Csc6  OBJECT IDENTIFIER
    ::= { cevModuleFabricType 14 }

-- GSR 12406 Clock Scheduler Card

cev12410Sfc10  OBJECT IDENTIFIER
    ::= { cevModuleFabricType 15 }

-- GSR 12410 Switch Fabric Card

cev12410Csc10  OBJECT IDENTIFIER
    ::= { cevModuleFabricType 16 }

-- GSR 12410 Clock Scheduler Card

cev12404Csc64  OBJECT IDENTIFIER
    ::= { cevModuleFabricType 17 }

-- GSR 12404 Fabric and Alarm card

cev12816Csc16Oc768  OBJECT IDENTIFIER
    ::= { cevModuleFabricType 18 }

-- GSR 12816 Clock Scheduler Card

cev12810Csc10Oc768  OBJECT IDENTIFIER
    ::= { cevModuleFabricType 19 }

-- GSR 12810 Clock Scheduler Card

cev12810Sfc10Oc768  OBJECT IDENTIFIER
    ::= { cevModuleFabricType 20 }

-- GSR 12810 Switch Fabric Card

cev12816Sfc16Oc768  OBJECT IDENTIFIER
    ::= { cevModuleFabricType 21 }

-- GSR 12816 Switch Fabric Card

cev12006CscAdvncd  OBJECT IDENTIFIER
    ::= { cevModuleFabricType 22 }

-- GSR 12006/12406 Advanced Clock scheduler card

cev12010CscAdvncd  OBJECT IDENTIFIER
    ::= { cevModuleFabricType 23 }

-- GSR 12010/12410 Advanced Clock scheduler card

cev12016CscAdvncd  OBJECT IDENTIFIER
    ::= { cevModuleFabricType 24 }

-- GSR 12016/12416 Advanced Clock scheduler card

cev12006SfcAdvncd  OBJECT IDENTIFIER
    ::= { cevModuleFabricType 25 }

-- GSR 12006/12406 Advanced Switch Fabric Card

cev12010SfcAdvncd  OBJECT IDENTIFIER
    ::= { cevModuleFabricType 26 }

-- GSR 12010/12410 Advanced Switch Fabric Card

cev12016SfcAdvncd  OBJECT IDENTIFIER
    ::= { cevModuleFabricType 27 }

-- GSR 12016/12416 Advanced Switch Fabric Card

cev12004FabAdvncd  OBJECT IDENTIFIER
    ::= { cevModuleFabricType 28 }

-- GSR 12004/12404 Advanced Collapsed Fabric/Alarm card

cev12816Csc16Oc768B  OBJECT IDENTIFIER
    ::= { cevModuleFabricType 29 }

-- GSR 12816 Enhanced Clock Scheduler Card

cev12810Csc10Oc768B  OBJECT IDENTIFIER
    ::= { cevModuleFabricType 30 }

-- GSR 12810 Enhanced Clock Scheduler Card

cevModuleDaughterCard  OBJECT IDENTIFIER
    ::= { cevModule 15 }

cevDslamNi2Controller  OBJECT IDENTIFIER
    ::= { cevModuleDaughterCard 4 }

-- Cisco 6100, 6130, 6260 DSLAM chassis NI-2 IOS controller Daughter Card

cevWvic2dsuE1DiG703  OBJECT IDENTIFIER
    ::= { cevModuleDaughterCard 5 }

-- Two port E1 voice interface daughtercard with Drop and Insert and G.703 for 2600 series and 3600 series routers

cevWvic1dsuE1G703  OBJECT IDENTIFIER
    ::= { cevModuleDaughterCard 6 }

-- One port E1 voice interface daughtercard with G.703 for 2600 series and 3600 series routers

cevDspmPvdm3  OBJECT IDENTIFIER
    ::= { cevModuleDaughterCard 7 }

-- Packet Voice DSP module with 3 C549 DSP's used by 17x0, 26x0, and 36x0 platforms

cevDspmPvdm1  OBJECT IDENTIFIER
    ::= { cevModuleDaughterCard 12 }

-- Packet Voice DSP module with 1 C549 DSP used by 17x0, 26x0, and 36x0 platforms

cevDspmPvdm2  OBJECT IDENTIFIER
    ::= { cevModuleDaughterCard 13 }

-- Packet Voice DSP module with 2 C549 DSPs used by 17x0, 26x0, and 36x0 platforms

cevDspmPvdm4  OBJECT IDENTIFIER
    ::= { cevModuleDaughterCard 14 }

-- Packet Voice DSP module with 4 C549 DSPs used by 17x0, 26x0, and 36x0 platforms

cevDspmPvdm5  OBJECT IDENTIFIER
    ::= { cevModuleDaughterCard 15 }

-- Packet Voice DSP module with 5 C549 DSPs used by 17x0, 26x0, and 36x0 platforms

cevHdaEm10fxs  OBJECT IDENTIFIER
    ::= { cevModuleDaughterCard 17 }

-- 10-port FXS Voice Interface Daughtercard

cevHdaEm4dsp  OBJECT IDENTIFIER
    ::= { cevModuleDaughterCard 18 }

-- 4-C5421 DSP Daughtercard

cevC7300Nse100Db  OBJECT IDENTIFIER
    ::= { cevModuleDaughterCard 19 }

-- Network Service Engine 100 Daughtercard for Cisco 7300 platform

cevCeScsi2636  OBJECT IDENTIFIER
    ::= { cevModuleDaughterCard 24 }

-- SCSI daughter card used by   Content Engine Modules for 26xx and 36xx series platforms

cevCeIde2636  OBJECT IDENTIFIER
    ::= { cevModuleDaughterCard 25 }

-- IDE daughter card used by   Content Engine Modules for 26xx and 36xx series platforms

cevVic4vpFxs4Did  OBJECT IDENTIFIER
    ::= { cevModuleDaughterCard 26 }

-- 4-port Direct Inward Dialing (DID) and 4-port Foreign Exchange Station (FXS) Voice Interface Daughtercard

cevC7300Nse100PlusDb  OBJECT IDENTIFIER
    ::= { cevModuleDaughterCard 27 }

-- Network Service Engine 100+ Daughtercard for Cisco 7300 platform

cevModuleCat4000DaughterCardType  OBJECT IDENTIFIER
    ::= { cevModuleDaughterCard 28 }

-- Catalyst 4000 Daughter Cards

cevCat4kDCWsf4531  OBJECT IDENTIFIER
    ::= { cevModuleCat4000DaughterCardType 1 }

-- NFFC(Netflow Feature Card) supervisor daughter card

cevCat4kDCWsu4504FxMt  OBJECT IDENTIFIER
    ::= { cevModuleCat4000DaughterCardType 2 }

-- Daughter Card with 4 100-Base FX uplink ports

cevVwic2Mft1T1E1  OBJECT IDENTIFIER
    ::= { cevModuleDaughterCard 29 }

-- VWIC2-1MFT-T1E1 (1 Port) RJ-48 Multi-Flex Trunk -T1/E1

cevVwic2Mft1G703  OBJECT IDENTIFIER
    ::= { cevModuleDaughterCard 30 }

-- VWIC2-1MFT-G703 (1 Port) RJ-48 Multi-Flex Trunk - G.703

cevVwic2Mft2T1E1  OBJECT IDENTIFIER
    ::= { cevModuleDaughterCard 31 }

-- VWIC2-2MFT-T1E1 (2 Port) RJ-48 Multi-Flex Trunk - T1/E1

cevVwic2Mft2G703  OBJECT IDENTIFIER
    ::= { cevModuleDaughterCard 32 }

-- VWIC2-2MFT-G703 (2 Port)) RJ-48 Multi-Flex Trunk - G.703

cevEcMft32  OBJECT IDENTIFIER
    ::= { cevModuleDaughterCard 33 }

-- EC-MFT-32 - 32-Channel Echo Canceller Module for Multiflex Trunk

cevEcMft64  OBJECT IDENTIFIER
    ::= { cevModuleDaughterCard 34 }

-- EC-MFT-64 - 64-Channel Echo Canceller Module for Multiflex Trunk

cevEm4Fxs4Fxo  OBJECT IDENTIFIER
    ::= { cevModuleDaughterCard 35 }

-- 8-port voice/fax expansion module - 4FXS/4FXO

cevEm6Fxo  OBJECT IDENTIFIER
    ::= { cevModuleDaughterCard 36 }

-- 6-port voice/fax expansion module - FXO

cevEm4BriNtTe  OBJECT IDENTIFIER
    ::= { cevModuleDaughterCard 37 }

-- 4-port voice/fax expansion module - BRI

cevpvdm2dsphalf  OBJECT IDENTIFIER
    ::= { cevModuleDaughterCard 38 }

-- Packet Voice C5510 DSP Module II with half channel capacity of C5510 DSP.

cevpvdm2dsp4  OBJECT IDENTIFIER
    ::= { cevModuleDaughterCard 39 }

-- Packet Voice C5510 DSP Module II with Four DSP in it

cevpvdm2dsp3  OBJECT IDENTIFIER
    ::= { cevModuleDaughterCard 40 }

-- Packet Voice C5510 DSP Module II with three DSP in it

cevpvdm2dsp2  OBJECT IDENTIFIER
    ::= { cevModuleDaughterCard 41 }

-- Packet Voice C5510 DSP Module II with two DSP in it

cevpvdm2dsp1  OBJECT IDENTIFIER
    ::= { cevModuleDaughterCard 42 }

-- Packet Voice C5510 DSP Module II with one DSP in it

cevpvdm2hwecan3  OBJECT IDENTIFIER
    ::= { cevModuleDaughterCard 43 }

-- Packet Voice C5510 DSP Module II Supports Hardware Echo cancel with 128 channels at 64 milli seconds tail-length

cevpvdm2hwecan2  OBJECT IDENTIFIER
    ::= { cevModuleDaughterCard 44 }

-- Packet Voice C5510 DSP Module II Supports Hardware Echo cancel with 64 channels at 64 milli seconds tail-length

cevpvdm2hwecan1  OBJECT IDENTIFIER
    ::= { cevModuleDaughterCard 45 }

-- Packet Voice C5510 DSP Module II Supports Hardware Echo cancel with 32 channels at 64 milli seconds tail-length

cevNetworkProcessor  OBJECT IDENTIFIER
    ::= { cevModuleDaughterCard 46 }

-- Network Processor card

cevVic2Mft1T1E1  OBJECT IDENTIFIER
    ::= { cevModuleDaughterCard 47 }

-- 1-Port RJ-48 Multiflex Voice Trunk - T1/E1

cevVic2Mft2T1E1  OBJECT IDENTIFIER
    ::= { cevModuleDaughterCard 48 }

-- 2-Port RJ-48 Multiflex Voice Trunk - T1/E1

cevEm2Hda4Fxo  OBJECT IDENTIFIER
    ::= { cevModuleDaughterCard 49 }

-- 4-port voice/fax expansion module - FXO

cevVic1J1  OBJECT IDENTIFIER
    ::= { cevModuleDaughterCard 50 }

-- VIC-1J1,Digital Voice J1 Interface with a single port DB-15 Connector for 2600, 3600 and 3700 series

cevWic1amV2  OBJECT IDENTIFIER
    ::= { cevModuleDaughterCard 51 }

-- WAN Interface Card - 1 Port Analog Modem

cevWic2amV2  OBJECT IDENTIFIER
    ::= { cevModuleDaughterCard 52 }

-- WAN Interface Card - 2 port Analog Modem

cevPvdmII12dm  OBJECT IDENTIFIER
    ::= { cevModuleDaughterCard 53 }

-- 12-port digital modem PVDM II  (Packet Voice Data Module - II)

cevVwic2T1E1Ran  OBJECT IDENTIFIER
    ::= { cevModuleDaughterCard 59 }

-- 2-Port T1/E1 WAN interface card with protection relays and 3GPP RAN Optimization support

cev7300Nse150Db  OBJECT IDENTIFIER
    ::= { cevModuleDaughterCard 60 }

-- Network Services Engine 150 Daughtercard for the Cisco 7304 platform

cevVic3Em2  OBJECT IDENTIFIER
    ::= { cevModuleDaughterCard 61 }

-- 3rd generation two port EM voice interface daughtercard

cevVic3FxsDid2  OBJECT IDENTIFIER
    ::= { cevModuleDaughterCard 62 }

-- 3rd generation two port FXS DID voice interface daughtercard

cevVic3FxsDid4  OBJECT IDENTIFIER
    ::= { cevModuleDaughterCard 63 }

-- 3rd generation four port FXS DID voice interface daughtercard

cevHdaEm3FxsDid8  OBJECT IDENTIFIER
    ::= { cevModuleDaughterCard 64 }

-- 3rd generation eight port FXS DID voice interface daughtercard

cev1DOCSIS20CableModemDC  OBJECT IDENTIFIER
    ::= { cevModuleDaughterCard 65 }

-- One port DOCSIS 2.0 cable modem daughter card

cev1DOCSIS20CableModemDCEJ  OBJECT IDENTIFIER
    ::= { cevModuleDaughterCard 66 }

-- One port Euro-DOCSIS/J-DOCSIS 2.0 cable modem daughter card

cevAsmM2900Top  OBJECT IDENTIFIER
    ::= { cevModuleDaughterCard 67 }

-- Timing over Packet Accessory Serivce Module for the Cisco MWR 2900 Series Mobile Wireless Routers

cevVic3FxsEDid2  OBJECT IDENTIFIER
    ::= { cevModuleDaughterCard 68 }

-- 3rd generation two port FXS Extended DID voice interface daughtercard

cevModuleASR9KLCDb  OBJECT IDENTIFIER
    ::= { cevModuleDaughterCard 69 }

-- Cisco ASR9K Generic LC Daughter Board

cevModemWan3g  OBJECT IDENTIFIER
    ::= { cevModuleDaughterCard 70 }

-- 3G WAN Modem Card

cevModulePVDM3c64  OBJECT IDENTIFIER
    ::= { cevModuleDaughterCard 73 }

-- PVDM3-64 (packet voice DSP module) is the next-generation Digital Signal Processor(DSP) module with 64 channels supporting high-density voice and video

cevModulePVDM3c32  OBJECT IDENTIFIER
    ::= { cevModuleDaughterCard 74 }

-- PVDM3-32 (packet voice DSP module) is the next-generation Digital Signal Processor(DSP) module with 32 channels supporting high-density voice and video

cevModulePVDM3c128  OBJECT IDENTIFIER
    ::= { cevModuleDaughterCard 75 }

-- PVDM3-128 (packet voice DSP module) is the next-generation Digital Signal Processor(DSP) module with 128 channels supporting high-density voice and video

cevModulePVDM3c192  OBJECT IDENTIFIER
    ::= { cevModuleDaughterCard 76 }

-- PVDM3-192 (packet voice DSP module) is the next-generation Digital Signal Processor(DSP) module with 192 channels supporting high-density voice and video

cevModulePVDM3c256  OBJECT IDENTIFIER
    ::= { cevModuleDaughterCard 77 }

-- PVDM3-256 (packet voice DSP module) is the next-generation Digital Signal Processor(DSP) module with 256 channels supporting high-density voice and video

cevNM2838  OBJECT IDENTIFIER
    ::= { cevModuleDaughterCard 78 }

-- Integrated Service Engine daughter card used by Service Modules for 28xx and 38xx series platforms

cevPANO2838  OBJECT IDENTIFIER
    ::= { cevModuleDaughterCard 79 }

-- Video Service Engine daughter card used by Service Modules for 28xx and 38xx series platforms

cevVwic3Mft4T1E1  OBJECT IDENTIFIER
    ::= { cevModuleDaughterCard 82 }

-- VWIC3-4MFT-T1E1 (4 Port) RJ-48 Multi-Flex Trunk -T1/E1

cevVwic3Mft1T1E1  OBJECT IDENTIFIER
    ::= { cevModuleDaughterCard 83 }

-- VWIC3-1MFT-T1E1 (1 Port) RJ-48 Multi-Flex Trunk -T1/E1

cevVwic3Mft1G703  OBJECT IDENTIFIER
    ::= { cevModuleDaughterCard 84 }

-- VWIC3-1MFT-G703 (1 Port) RJ-48 Multi-Flex Trunk - G.703

cevVwic3Mft2T1E1  OBJECT IDENTIFIER
    ::= { cevModuleDaughterCard 85 }

-- VWIC3-2MFT-T1E1 (2 Port) RJ-48 Multi-Flex Trunk -T1/E1

cevVwic3Mft2G703  OBJECT IDENTIFIER
    ::= { cevModuleDaughterCard 86 }

-- VWIC3-2MFT-G703 (2 Port) RJ-48 Multi-Flex Trunk - G.703

cevPrp3Smdc  OBJECT IDENTIFIER
    ::= { cevModuleDaughterCard 87 }

-- New daughter card for the route processor card on c12000. Please refer to EDCS-883053 for more details

cevPWic1AmV2  OBJECT IDENTIFIER
    ::= { cevModuleDaughterCard 93 }

-- one-port Analog Modem Interface card

cevPVwic3Mft1G703  OBJECT IDENTIFIER
    ::= { cevModuleDaughterCard 94 }

-- 1-Port 3rd Gen Multiflex Trunk Voice/WAN Int. Card - G.703

cevPVwic3Mft1T1E1  OBJECT IDENTIFIER
    ::= { cevModuleDaughterCard 95 }

-- 1-Port 3rd Gen Multiflex Trunk Voice/WAN Int. Card - T1/E1

cevPVwic3Mft2G703  OBJECT IDENTIFIER
    ::= { cevModuleDaughterCard 96 }

-- 2-Port 3rd Gen Multiflex Trunk Voice/WAN Int. Card - G.703

cevPVwic3Mft2T1E1  OBJECT IDENTIFIER
    ::= { cevModuleDaughterCard 97 }

-- 2-Port 3rd Gen Multiflex Trunk Voice/WAN Int. Card - T1/E1

cevPVwic3Mft4T1E1  OBJECT IDENTIFIER
    ::= { cevModuleDaughterCard 98 }

-- 4-Port 3rd Gen Multiflex Trunk Voice/WAN Int. Card - T1/E1

cevModulePPVDM3c128  OBJECT IDENTIFIER
    ::= { cevModuleDaughterCard 99 }

-- 128-channel high-density voice and video DSP module

cevModulePPVDM3c16  OBJECT IDENTIFIER
    ::= { cevModuleDaughterCard 100 }

-- 16-channel high-density voice and video DSP module

cevModulePPVDM3c192  OBJECT IDENTIFIER
    ::= { cevModuleDaughterCard 101 }

-- 192-channel high-density voice and video DSP module

cevModulePPVDM3c256  OBJECT IDENTIFIER
    ::= { cevModuleDaughterCard 102 }

-- 256-channel high-density voice and video DSP module

cevModulePPVDM3c32  OBJECT IDENTIFIER
    ::= { cevModuleDaughterCard 103 }

-- 32-channel high-density voice and video DSP module

cevModulePPVDM3c64  OBJECT IDENTIFIER
    ::= { cevModuleDaughterCard 104 }

-- 64-channel high-density voice and video DSP module

cevPVic3Em2  OBJECT IDENTIFIER
    ::= { cevModuleDaughterCard 105 }

-- Two-port Voice Interface Card - E and M

cevPVic3Fxs2Did  OBJECT IDENTIFIER
    ::= { cevModuleDaughterCard 106 }

-- Two-Port Voice Interface Card- FXS and DID

cevPVic3Fxs4Did  OBJECT IDENTIFIER
    ::= { cevModuleDaughterCard 107 }

-- Four-Port Voice Interface Card - FXS and DID

cevModuleGBICs  OBJECT IDENTIFIER
    ::= { cevModule 16 }

cevMGBIC1000BaseLX  OBJECT IDENTIFIER
    ::= { cevModuleGBICs 1 }

-- longwave fiber gigabit ethernet port adapter

cevMGBIC1000BaseSX  OBJECT IDENTIFIER
    ::= { cevModuleGBICs 2 }

-- shortwave fiber gigabit ethernet port adapter

cevMGBIC1000BaseCX  OBJECT IDENTIFIER
    ::= { cevModuleGBICs 3 }

-- copper wire gigabit ethernet port adapter

cevMGBIC1000BaseLH  OBJECT IDENTIFIER
    ::= { cevModuleGBICs 4 }

-- longhaul multimode fiber gigabit ethernet port adapter

cevMGBIC1000BaseZX  OBJECT IDENTIFIER
    ::= { cevModuleGBICs 5 }

-- extended reach singlemode fiber gigabit ethernet port adapter

cevMGBIC1000BaseCXSTACK  OBJECT IDENTIFIER
    ::= { cevModuleGBICs 6 }

-- Cisco gigaStack gigabit ethernet port adapter

cevMGBIC1000BaseT  OBJECT IDENTIFIER
    ::= { cevModuleGBICs 7 }

-- Copper Unshielded twisted pair gigabit ethernet port adapter

cevMGBICDWDM6061  OBJECT IDENTIFIER
    ::= { cevModuleGBICs 16 }

-- DWDM wavelength 1560.61 nm gigabit ethernet port adapter

cevMGBICDWDM5979  OBJECT IDENTIFIER
    ::= { cevModuleGBICs 17 }

-- DWDM wavelength 1559.79 nm gigabit ethernet port adapter

cevMGBICDWDM5898  OBJECT IDENTIFIER
    ::= { cevModuleGBICs 18 }

-- DWDM wavelength 1558.98 nm gigabit ethernet port adapter

cevMGBICDWDM5817  OBJECT IDENTIFIER
    ::= { cevModuleGBICs 19 }

-- DWDM wavelength 1558.17 nm gigabit ethernet port adapter

cevMGBICDWDM5655  OBJECT IDENTIFIER
    ::= { cevModuleGBICs 20 }

-- DWDM wavelength 1556.55 nm gigabit ethernet port adapter

cevMGBICDWDM5575  OBJECT IDENTIFIER
    ::= { cevModuleGBICs 21 }

-- DWDM wavelength 1555.75 nm gigabit ethernet port adapter

cevMGBICDWDM5494  OBJECT IDENTIFIER
    ::= { cevModuleGBICs 22 }

-- DWDM wavelength 1554.94 nm gigabit ethernet port adapter

cevMGBICDWDM5413  OBJECT IDENTIFIER
    ::= { cevModuleGBICs 23 }

-- DWDM wavelength 1554.13 nm gigabit ethernet port adapter

cevMGBICDWDM5252  OBJECT IDENTIFIER
    ::= { cevModuleGBICs 24 }

-- DWDM wavelength 1552.52 nm gigabit ethernet port adapter

cevMGBICDWDM5172  OBJECT IDENTIFIER
    ::= { cevModuleGBICs 25 }

-- DWDM wavelength 1551.72 nm gigabit ethernet port adapter

cevMGBICDWDM5092  OBJECT IDENTIFIER
    ::= { cevModuleGBICs 26 }

-- DWDM wavelength 1550.92 nm gigabit ethernet port adapter

cevMGBICDWDM5012  OBJECT IDENTIFIER
    ::= { cevModuleGBICs 27 }

-- DWDM wavelength 1550.12 nm gigabit ethernet port adapter

cevMGBICDWDM4851  OBJECT IDENTIFIER
    ::= { cevModuleGBICs 28 }

-- DWDM wavelength 1548.51 nm gigabit ethernet port adapter

cevMGBICDWDM4772  OBJECT IDENTIFIER
    ::= { cevModuleGBICs 29 }

-- DWDM wavelength 1547.72 nm gigabit ethernet port adapter

cevMGBICDWDM4692  OBJECT IDENTIFIER
    ::= { cevModuleGBICs 30 }

-- DWDM wavelength 1546.92 nm gigabit ethernet port adapter

cevMGBICDWDM4612  OBJECT IDENTIFIER
    ::= { cevModuleGBICs 31 }

-- DWDM wavelength 1546.12 nm gigabit ethernet port adapter

cevMGBICDWDM4453  OBJECT IDENTIFIER
    ::= { cevModuleGBICs 32 }

-- DWDM wavelength 1544.53 nm gigabit ethernet port adapter

cevMGBICDWDM4373  OBJECT IDENTIFIER
    ::= { cevModuleGBICs 33 }

-- DWDM wavelength 1543.73 nm gigabit ethernet port adapter

cevMGBICDWDM4294  OBJECT IDENTIFIER
    ::= { cevModuleGBICs 34 }

-- DWDM wavelength 1542.94 nm gigabit ethernet port adapter

cevMGBICDWDM4214  OBJECT IDENTIFIER
    ::= { cevModuleGBICs 35 }

-- DWDM wavelength 1542.14 nm gigabit ethernet port adapter

cevMGBICDWDM4056  OBJECT IDENTIFIER
    ::= { cevModuleGBICs 36 }

-- DWDM wavelength 1540.56 nm gigabit ethernet port adapter

cevMGBICDWDM3977  OBJECT IDENTIFIER
    ::= { cevModuleGBICs 37 }

-- DWDM wavelength 1539.77 nm gigabit ethernet port adapter

cevMGBICDWDM3898  OBJECT IDENTIFIER
    ::= { cevModuleGBICs 38 }

-- DWDM wavelength 1538.98 nm gigabit ethernet port adapter

cevMGBICDWDM3819  OBJECT IDENTIFIER
    ::= { cevModuleGBICs 39 }

-- DWDM wavelength 1538.19 nm gigabit ethernet port adapter

cevMGBICDWDM3661  OBJECT IDENTIFIER
    ::= { cevModuleGBICs 40 }

-- DWDM wavelength 1536.61 nm gigabit ethernet port adapter

cevMGBICDWDM3582  OBJECT IDENTIFIER
    ::= { cevModuleGBICs 41 }

-- DWDM wavelength 1535.82 nm gigabit ethernet port adapter

cevMGBICDWDM3504  OBJECT IDENTIFIER
    ::= { cevModuleGBICs 42 }

-- DWDM wavelength 1535.04 nm gigabit ethernet port adapter

cevMGBICDWDM3425  OBJECT IDENTIFIER
    ::= { cevModuleGBICs 43 }

-- DWDM wavelength 1534.25 nm gigabit ethernet port adapter

cevMGBICDWDM3268  OBJECT IDENTIFIER
    ::= { cevModuleGBICs 44 }

-- DWDM wavelength 1532.68 nm gigabit ethernet port adapter

cevMGBICDWDM3190  OBJECT IDENTIFIER
    ::= { cevModuleGBICs 45 }

-- DWDM wavelength 1531.90 nm gigabit ethernet port adapter

cevMGBICDWDM3112  OBJECT IDENTIFIER
    ::= { cevModuleGBICs 46 }

-- DWDM wavelength 1531.12 nm gigabit ethernet port adapter

cevMGBICDWDM3033  OBJECT IDENTIFIER
    ::= { cevModuleGBICs 47 }

-- DWDM wavelength 1530.33 nm gigabit ethernet port adapter

cevMGBICXWDMRxOnly  OBJECT IDENTIFIER
    ::= { cevModuleGBICs 48 }

-- XWDM receive-only gigabit ethernet port adapter

cevMGBIC1490BaseBX10D  OBJECT IDENTIFIER
    ::= { cevModuleGBICs 49 }

-- BX10-D 1490 nm Tx bi-directional fiber gigabit ethernet port adapter

cevMGBIC1310BaseBX10U  OBJECT IDENTIFIER
    ::= { cevModuleGBICs 50 }

-- BX10-U 1310 nm Tx bi-directional fiber gigabit ethernet port adapter

cevMGBICDWDM6141  OBJECT IDENTIFIER
    ::= { cevModuleGBICs 51 }

-- DWDM wavelength 1561.42 nm gigabit ethernet port adapter

cevMGBICDWDM5736  OBJECT IDENTIFIER
    ::= { cevModuleGBICs 52 }

-- DWDM wavelength 1557.36 nm gigabit ethernet port adapter

cevMGBICDWDM5332  OBJECT IDENTIFIER
    ::= { cevModuleGBICs 53 }

-- DWDM wavelength 1553.33 nm gigabit ethernet port adapter

cevMGBICDWDM4931  OBJECT IDENTIFIER
    ::= { cevModuleGBICs 54 }

-- DWDM wavelength 1549.32 nm gigabit ethernet port adapter

cevMGBICDWDM4532  OBJECT IDENTIFIER
    ::= { cevModuleGBICs 55 }

-- DWDM wavelength 1545.32 nm gigabit ethernet port adapter

cevMGBICDWDM4134  OBJECT IDENTIFIER
    ::= { cevModuleGBICs 56 }

-- DWDM wavelength 1541.35 nm gigabit ethernet port adapter

cevMGBICDWDM3739  OBJECT IDENTIFIER
    ::= { cevModuleGBICs 57 }

-- DWDM wavelength 1537.40 nm gigabit ethernet port adapter

cevMGBICDWDM3346  OBJECT IDENTIFIER
    ::= { cevModuleGBICs 58 }

-- DWDM wavelength 1533.47 nm gigabit ethernet port adapter

cevModuleC6xxxType  OBJECT IDENTIFIER
    ::= { cevModule 17 }

cevC6xxxSlcCap8  OBJECT IDENTIFIER
    ::= { cevModuleC6xxxType 1 }

-- Subscriber line card for c6200 - Carrierless Amplitude and Phase modulation, 8 port variation

cevC6xxxNtcOc3si  OBJECT IDENTIFIER
    ::= { cevModuleC6xxxType 2 }

-- Network Trunk card for c6200 - Optical Carrier 3, single-mode, intermediate reach variation

cevC6xxxNtcOc3mm  OBJECT IDENTIFIER
    ::= { cevModuleC6xxxType 3 }

-- Network Trunk Card for c6200 - Optical Carrier 3, multi-mode variation

cevC6xxxNtcStm1si  OBJECT IDENTIFIER
    ::= { cevModuleC6xxxType 4 }

-- Network Trunk Card for c6200 - Synchronous Transport Module level 1, single-mode, intermediate reach variation

cevC6xxxNtcStm1mm  OBJECT IDENTIFIER
    ::= { cevModuleC6xxxType 5 }

-- Network Trunk Card for c6200 - Synchronous Transport Module level 1, multi-mode variation

cevC6xxxSlcDmt8  OBJECT IDENTIFIER
    ::= { cevModuleC6xxxType 6 }

-- Subscriber line card for c6200 - Discrete Multi-Tone, 8 port variation

cevC6xxxSlcDmt16  OBJECT IDENTIFIER
    ::= { cevModuleC6xxxType 7 }

-- Subscriber line card for c6200 - Discrete Multi-Tone, 16 port variation

cevC6xxxNtcDs3  OBJECT IDENTIFIER
    ::= { cevModuleC6xxxType 8 }

-- Network Trunk card for c6200 - DS3

cevC6xxxOsm1Oc48PosSs  OBJECT IDENTIFIER
    ::= { cevModuleC6xxxType 10 }

-- Optical Service Module, 1-Port OC48 POS SS w/ 4 GE

cevC6xxxOsm1Oc48PosSl  OBJECT IDENTIFIER
    ::= { cevModuleC6xxxType 11 }

-- Optical Service Module, 1-Port OC48 POS SL w/ 4 GE

cevC6xxxOsm1Oc48PosSi  OBJECT IDENTIFIER
    ::= { cevModuleC6xxxType 12 }

-- Optical Service Module, 1-Port OC48 POS SI w/ 4 GE

cevC6xxxOsm2Oc12PosSl  OBJECT IDENTIFIER
    ::= { cevModuleC6xxxType 15 }

-- Optical Service Module, 2-Port OC12 POS SL w/ 4 GE

cevC6xxxOsm4Oc12PosSl  OBJECT IDENTIFIER
    ::= { cevModuleC6xxxType 16 }

-- Optical Service Module, 4-Port OC12 POS SL w/ 4 GE

cevC6xxxOsm2Oc12PosMm  OBJECT IDENTIFIER
    ::= { cevModuleC6xxxType 17 }

-- Optical Service Module, 2-Port OC12 POS MM w/ 4 GE

cevC6xxxOsm4Oc12PosMm  OBJECT IDENTIFIER
    ::= { cevModuleC6xxxType 18 }

-- Optical Service Module, 4-Port OC12 POS MM w/ 4 GE

cevC6xxxOsm2Oc12PosSi  OBJECT IDENTIFIER
    ::= { cevModuleC6xxxType 19 }

-- Optical Service Module, 2-Port OC12 POS SI w/ 4 GE

cevC6xxxOsm4Oc12PosSi  OBJECT IDENTIFIER
    ::= { cevModuleC6xxxType 20 }

-- Optical Service Module, 4-Port OC12 POS SI w/ 4 GE

cevC6xxxOsm8Oc3PosSi  OBJECT IDENTIFIER
    ::= { cevModuleC6xxxType 21 }

-- Optical Service Module, 8-Port OC3 POS SI w/ 4 GE

cevC6xxxOsm16Oc3PosSi  OBJECT IDENTIFIER
    ::= { cevModuleC6xxxType 22 }

-- Optical Service Module, 16-Port OC3 POS SI w/ 4 GE

cevC6xxxOsm8Oc3PosMm  OBJECT IDENTIFIER
    ::= { cevModuleC6xxxType 23 }

-- Optical Service Module, 8-Port OC3 POS MM w/ 4 GE

cevC6xxxOsm16Oc3PosMm  OBJECT IDENTIFIER
    ::= { cevModuleC6xxxType 24 }

-- Optical Service Module, 16-Port OC3 POS MM w/ 4 GE

cevC6xxxOsm8Oc3PosSl  OBJECT IDENTIFIER
    ::= { cevModuleC6xxxType 25 }

-- Optical Service Module, 8-Port OC3 POS SL w/ 4 GE

cevC6xxxOsm16Oc3PosSl  OBJECT IDENTIFIER
    ::= { cevModuleC6xxxType 26 }

-- Optical Service Module, 16-Port OC3 POS SL w/ 4 GE

cevC6xxx4GeWanGbic  OBJECT IDENTIFIER
    ::= { cevModuleC6xxxType 27 }

-- Optical Service Module, 4-Port GE w/ WAN services

cevC6xxxOsm4ge4oc12ChDs3SmIr  OBJECT IDENTIFIER
    ::= { cevModuleC6xxxType 31 }

-- Optical Service Module, 4-Port OC12 channelized down to DS3 Singlemode Intermediate range with 4 GE

cevC6xxxOsm4ge8oc12ChDs3SmIr  OBJECT IDENTIFIER
    ::= { cevModuleC6xxxType 32 }

-- Optical Service Module, 8-Port OC12 channelized down to DS3 Singlemode Intermediate range with 4 GE

cevC6xxxOsm4geoc48ChDs3SmSr  OBJECT IDENTIFIER
    ::= { cevModuleC6xxxType 33 }

-- Optical Service Module, 1-Port OC48 channelized down to DS3 Singlemode Short range with 4 GE

ceC6xxxOsm4ge2oc48ChDs3SmSr  OBJECT IDENTIFIER
    ::= { cevModuleC6xxxType 34 }

-- Optical Service Module, 2-Port OC48 channelized down to DS3 Singlemode Short range with 4 GE

cevC6xxxOsm4geoc48ChDs3SmIr  OBJECT IDENTIFIER
    ::= { cevModuleC6xxxType 35 }

-- Optical Service Module, 1-Port OC48 channelized down to DS3 Singlemode Intermediate range with 4 GE

cevC6xxxOsm4ge2oc48ChDs3SmIr  OBJECT IDENTIFIER
    ::= { cevModuleC6xxxType 36 }

-- Optical Service Module, 2-Port OC48 channelized down to DS3 Singlemode Intermediate range with 4 GE

cevC6xxxOsm4geoc12ChDs3SmIr  OBJECT IDENTIFIER
    ::= { cevModuleC6xxxType 37 }

-- Optical Service Module, 1-Port OC12 channelized down to DS3 Single Mode Intermediate range with 4 GE

cevC6xxxOsm4ge2oc12ChDs3SmIr  OBJECT IDENTIFIER
    ::= { cevModuleC6xxxType 38 }

-- Optical Service Module, 2-Port OC12 channelized down to DS3 Single Mode Intermediate range with 4 GE

cevC6xxxOsm2Oc12AtmMmPlus  OBJECT IDENTIFIER
    ::= { cevModuleC6xxxType 40 }

-- Enhanced Optical Service Module, 2-Port OC12 ATM MM w/ 4 GE

cevC6xxxOsm2Oc12AtmSiPlus  OBJECT IDENTIFIER
    ::= { cevModuleC6xxxType 41 }

-- Enhanced Optical Service Module, 2-Port OC12 ATM SI w/ 4 GE

cevC6xxx4GeWanGbicPlus  OBJECT IDENTIFIER
    ::= { cevModuleC6xxxType 42 }

-- Enhanced Optical Service Module, 4-Port GE w/ WAN services

cevC6xxxOsm1Oc48PosSsPlus  OBJECT IDENTIFIER
    ::= { cevModuleC6xxxType 43 }

-- Enhanced Optical Service Module, 1-Port OC48 POS SS w/ 4 GE

cevC6xxxOsm1Oc48PosSiPlus  OBJECT IDENTIFIER
    ::= { cevModuleC6xxxType 44 }

-- Enhanced Optical Service Module, 1-Port OC48 POS SI w/ 4 GE

cevC6xxxOsm1Oc48PosSlPlus  OBJECT IDENTIFIER
    ::= { cevModuleC6xxxType 45 }

-- Enhanced Optical Service Module, 1-Port OC48 POS SL w/ 4 GE

cevC6xxxOsm4Oc12PosSiPlus  OBJECT IDENTIFIER
    ::= { cevModuleC6xxxType 46 }

-- Enhanced Optical Service Module, 4-Port OC12 POS SI w/ 4 GE

cevC6xxxOsm2Oc12PosMmPlus  OBJECT IDENTIFIER
    ::= { cevModuleC6xxxType 47 }

-- Enhanced Optical Service Module, 2-Port OC12 POS MM w/ 4 GE

cevC6xxxOsm4Oc3PosSiPlus  OBJECT IDENTIFIER
    ::= { cevModuleC6xxxType 48 }

-- Enhanced Optical Service Module, 4-Port OC3 POS SI w/ 4 GE

cevC6xxxOsm8Oc3PosSiPlus  OBJECT IDENTIFIER
    ::= { cevModuleC6xxxType 49 }

-- Enhanced Optical Service Module, 8-Port OC3 POS SI w/ 4 GE

cevC6xxxOsm8Oc3PosSlPlus  OBJECT IDENTIFIER
    ::= { cevModuleC6xxxType 50 }

-- Enhanced Optical Service Module, 8-Port OC3 POS SL w/ 4 GE

cevC6xxxOsm16Oc3PosSiPlus  OBJECT IDENTIFIER
    ::= { cevModuleC6xxxType 51 }

-- Enhanced Optical Service Module, 16-Port OC3 POS SI w/ 4 GE

cevC6xxxOsm12Ct3T1  OBJECT IDENTIFIER
    ::= { cevModuleC6xxxType 52 }

-- Optical Service Module, 12-Port DS3 Channelized T1/E1

cevC6xxxCwpa2  OBJECT IDENTIFIER
    ::= { cevModuleC6xxxType 53 }

-- Flexwan2 Linecard

cevC6xxxSIP200  OBJECT IDENTIFIER
    ::= { cevModuleC6xxxType 54 }

-- SIP1/SIP200 LC which holds the SPAs.

cevC6xxxSIP400  OBJECT IDENTIFIER
    ::= { cevModuleC6xxxType 55 }

-- SIP2/SIP400 LC which holds SPAs

cevC6xxxSIP600  OBJECT IDENTIFIER
    ::= { cevModuleC6xxxType 56 }

-- SIP2-10G/SIP600 LC which holds SPAs

cevC6xxxOsm2Oc12PosSiPlus  OBJECT IDENTIFIER
    ::= { cevModuleC6xxxType 57 }

-- Enhanced Optical Service Module, 2 port OC12 Pos SI w/4 GE

cevC6xxxOsm4Oc3PosSi  OBJECT IDENTIFIER
    ::= { cevModuleC6xxxType 58 }

-- Optical Service Module, 4 port OC3 POS SI w/ 4 GE

cevC6xxxOsm4Oc3PosSl  OBJECT IDENTIFIER
    ::= { cevModuleC6xxxType 59 }

-- Optical Service Module, 4 port OC3 POS SL w/ 4 GE

cevC6xxxOsm4Oc3PosMm  OBJECT IDENTIFIER
    ::= { cevModuleC6xxxType 60 }

-- Optical Service Module, 4 port OC3 POS MM w/ 4 GE

cevC6xxxOsm24Ct3T1  OBJECT IDENTIFIER
    ::= { cevModuleC6xxxType 61 }

-- Optical Service Module, 24 port DS3 Channelized T1/E1

cevCat6kWsx6600  OBJECT IDENTIFIER
    ::= { cevModuleC6xxxType 62 }

-- Catalyst 6000 Acess Gateway line card supporting voice and WAN (Wide Area Network)interfaces as well as conferencing and transcoding services

cevC6xxxSSC600  OBJECT IDENTIFIER
    ::= { cevModuleC6xxxType 63 }

-- SSC600 LC which holds the SPAs

cevC6xxxSSC400  OBJECT IDENTIFIER
    ::= { cevModuleC6xxxType 64 }

-- SSC400 LC which holds the SPAs

cevC6xxxRSP720Base  OBJECT IDENTIFIER
    ::= { cevModuleC6xxxType 65 }

-- C7600 Router Switch Processor Module 720 Base board

cevC6xxxRSP32GEBase  OBJECT IDENTIFIER
    ::= { cevModuleC6xxxType 66 }

-- C7600 Router Switch Processor Module 32 GE Base board

cevC6xxxRSP3210GEBase  OBJECT IDENTIFIER
    ::= { cevModuleC6xxxType 67 }

-- C7600 Router Switch Processor Module 32 - 10 GE Base board

cevC6xxxRSP720  OBJECT IDENTIFIER
    ::= { cevModuleC6xxxType 68 }

-- C7600 Route Switch Processor Module 720 CPU board

cevC6xxxRSP32  OBJECT IDENTIFIER
    ::= { cevModuleC6xxxType 69 }

-- C7600 Route Switch Processor Module 32 CPU board

cevC6xxxSIP600DC  OBJECT IDENTIFIER
    ::= { cevModuleC6xxxType 71 }

-- SIP 600 Distributed Forwarding Card

cevC6xxxRSP720MsfcNaboo  OBJECT IDENTIFIER
    ::= { cevModuleC6xxxType 72 }

-- RSP720 Multilevel Switching Feature Card

cevC6xxxRSP720PfcGanges  OBJECT IDENTIFIER
    ::= { cevModuleC6xxxType 73 }

-- RSP720 Policy Feature Card

cevC6xxxEsm20G  OBJECT IDENTIFIER
    ::= { cevModuleC6xxxType 74 }

-- 2x10G or 20x1G Ethernet Distributed Forwarding Line Card on Cisco 7600

cevC6xxxEsm20GCpuDc  OBJECT IDENTIFIER
    ::= { cevModuleC6xxxType 75 }

-- ESM20G CPU Daughter Card

cevC6xxxEsm20GPfc3CxlDc  OBJECT IDENTIFIER
    ::= { cevModuleC6xxxType 76 }

-- ESM20G Policy Forwarding 3CXL Daughter Card

cevC6xxxEsm20GPfc3CDc  OBJECT IDENTIFIER
    ::= { cevModuleC6xxxType 77 }

-- ESM20G Policy Forwarding 3C Daughter Card

cevC6xxxEsm20G2x10gDc  OBJECT IDENTIFIER
    ::= { cevModuleC6xxxType 78 }

-- ESM20G 2x10g Ethernet Link Daughter Card

cevC6xxxEsm20G20x1gDc  OBJECT IDENTIFIER
    ::= { cevModuleC6xxxType 79 }

-- ESM20G 20x1G Ethernet Link Daughter Card

cevC6xxxRSP72010GEBase  OBJECT IDENTIFIER
    ::= { cevModuleC6xxxType 80 }

-- C7600 Route Switch Processor Module 720 - 10 GE Base board

cevC6xxxEs20C3c  OBJECT IDENTIFIER
    ::= { cevModuleC6xxxType 81 }

-- 1x10GE,10x1G combo 3C

cevC6xxxEs40C3c  OBJECT IDENTIFIER
    ::= { cevModuleC6xxxType 82 }

-- 2x10GE,20x1G combo 3C

cevC6xxxEs20C3cxl  OBJECT IDENTIFIER
    ::= { cevModuleC6xxxType 83 }

-- 1x10GE,10x1G combo 3C XL

cevC6xxxEs40C3cxl  OBJECT IDENTIFIER
    ::= { cevModuleC6xxxType 84 }

-- 2x10GE,20x1G combo 3C XL

cevC6xxxEs20G3c  OBJECT IDENTIFIER
    ::= { cevModuleC6xxxType 85 }

-- Fixed 20x1GE with Pluggable Optics 3C

cevC6xxxEs2Tg3c  OBJECT IDENTIFIER
    ::= { cevModuleC6xxxType 86 }

-- Fixed 2x10GE with Pluggable Optics 3C

cevC6xxxEs40G3c  OBJECT IDENTIFIER
    ::= { cevModuleC6xxxType 87 }

-- Fixed 40x1GE with Pluggable Optics 3C

cevC6xxxEs4Tg3c  OBJECT IDENTIFIER
    ::= { cevModuleC6xxxType 88 }

-- Fixed 4x10GE with Pluggable Optics 3C

cevC6xxxEs20G3cxl  OBJECT IDENTIFIER
    ::= { cevModuleC6xxxType 89 }

-- Fixed 20x1GE with Pluggable Optics 3C XL

cevC6xxxEs2Tg3cxl  OBJECT IDENTIFIER
    ::= { cevModuleC6xxxType 90 }

-- Fixed 2x10GE with Pluggable Optics  3C XL

cevC6xxxEs40G3cxl  OBJECT IDENTIFIER
    ::= { cevModuleC6xxxType 91 }

-- Fixed 40x1GE with Pluggable Optics 3C XL

cevC6xxxEs4Tg3cxl  OBJECT IDENTIFIER
    ::= { cevModuleC6xxxType 92 }

-- Fixed 4x10GE with Pluggable Optics 3C XL

cevC6xxxMsfc4  OBJECT IDENTIFIER
    ::= { cevModuleC6xxxType 93 }

-- RSP720 Multilevel Switching Feature Card

cevC6xxxPfc3c  OBJECT IDENTIFIER
    ::= { cevModuleC6xxxType 94 }

-- RSP720 Policy Feature Card 3C

cevC6xxxPfc3cxl  OBJECT IDENTIFIER
    ::= { cevModuleC6xxxType 95 }

-- RSP720 Policy Feature Card 3C XL

cevC6xxxEs2Tg20GDc  OBJECT IDENTIFIER
    ::= { cevModuleC6xxxType 96 }

-- C7600 ES+ 2x10GE,20x1G combo Link Daughter Card

cevC6xxxEs1Tg10GDc  OBJECT IDENTIFIER
    ::= { cevModuleC6xxxType 97 }

-- C7600 ES+ 1x10GE,10x1G combo Link Daughter Card

cevC6xxxEsBase  OBJECT IDENTIFIER
    ::= { cevModuleC6xxxType 98 }

-- C7600 ES+ baseboard

cevC6xxxEsPfc3CxlDc  OBJECT IDENTIFIER
    ::= { cevModuleC6xxxType 99 }

-- 7600 ES+ Policy Forwarding 3CXL Daughter Card

cevC6xxxEsPfc3CDc  OBJECT IDENTIFIER
    ::= { cevModuleC6xxxType 100 }

-- C7600 ES+ Policy Forwarding 3C Daughter Card

cevC6xxxEs20GDc  OBJECT IDENTIFIER
    ::= { cevModuleC6xxxType 101 }

-- C7600 ES+ 20x1G Link Daughter Card

cevC6xxxEs2TgDc  OBJECT IDENTIFIER
    ::= { cevModuleC6xxxType 102 }

-- C7600 ES+ 2x10G Link Daughter Card

cevC6xxxEs40GDc  OBJECT IDENTIFIER
    ::= { cevModuleC6xxxType 103 }

-- C7600 ES+ 40x1G Link Daughter Card

cevC6xxxEs4TgDc  OBJECT IDENTIFIER
    ::= { cevModuleC6xxxType 104 }

-- C7600 ES+ 4x10G Link Daughter Card

cevC6xxxEsItu2TgDc  OBJECT IDENTIFIER
    ::= { cevModuleC6xxxType 105 }

-- C7600 ES+ OTN/DWDM+FEC 2x10GE Link Daughter Card

cevC6xxxEsItu4TgDc  OBJECT IDENTIFIER
    ::= { cevModuleC6xxxType 106 }

-- C7600 ES+ OTN/DWDM+FEC 4x10GE Link Daughter Card

cevC6xxxEsItu2Tg3cxl  OBJECT IDENTIFIER
    ::= { cevModuleC6xxxType 107 }

-- C7600 ES+ OTN/DWDM+FEC 2x10GE 3C XL

cevC6xxxEsItu4Tg3cxl  OBJECT IDENTIFIER
    ::= { cevModuleC6xxxType 108 }

-- C7600 ES+ OTN/DWDM+FEC 4x10GE 3C XL

cevC6xxxEsT  OBJECT IDENTIFIER
    ::= { cevModuleC6xxxType 109 }

-- C7600 ES+ Low Queue Baseboard

cevC6xxxEsItu2Tg3c  OBJECT IDENTIFIER
    ::= { cevModuleC6xxxType 110 }

-- C7600 ES+ OTN/DWDM+FEC 2x10GE 3C

cevC6xxxEsItu4Tg3c  OBJECT IDENTIFIER
    ::= { cevModuleC6xxxType 111 }

-- C7600 ES+ OTN/DWDM+FEC 4x10GE 3C XL

cevC6xxxEst20gDc  OBJECT IDENTIFIER
    ::= { cevModuleC6xxxType 112 }

-- C7600 ES+T 20x1G Low Queue Transport Link Daughter Card

cevC6xxxEst40gDc  OBJECT IDENTIFIER
    ::= { cevModuleC6xxxType 113 }

-- C7600 ES+T 40x1G Low Queue Transport Link Daughter Card

cevC6xxxEstItu2tgDc  OBJECT IDENTIFIER
    ::= { cevModuleC6xxxType 114 }

-- C7600 ES+T OTN/DWDM+FEC 2x10GE 3C XL Low Queue Transport Link Daughter card

cevC6xxxEstItu4tgDc  OBJECT IDENTIFIER
    ::= { cevModuleC6xxxType 115 }

-- C7600 ES+T OTN/DWDM+FEC 2x10GE 3C XL Low Queue Transport Link Daughter card

cevC6xxxEst20G3Cxl  OBJECT IDENTIFIER
    ::= { cevModuleC6xxxType 116 }

-- C7600 ES+T Fixed 20x1G Low Queue Transport 3CXL

cevC6xxxEst40G3Cxl  OBJECT IDENTIFIER
    ::= { cevModuleC6xxxType 117 }

-- C7600 ES+T Fixed 40x1G Low Queue Transport 3CXL

cevC6xxxEstItu2TG3Cxl  OBJECT IDENTIFIER
    ::= { cevModuleC6xxxType 118 }

-- C7600 ES+T Fixed OTN/DWDM+FEC 2x10GE 3C XL Low Queue Transport 3CXL

cevC6xxxEstItu4TG3Cxl  OBJECT IDENTIFIER
    ::= { cevModuleC6xxxType 119 }

-- C7600 ES+T Fixed OTN/DWDM+FEC 4x10GE 3C XL Low Queue Transport 3CXL

cevC6xxxEsTXc20G  OBJECT IDENTIFIER
    ::= { cevModuleC6xxxType 120 }

-- 7600 ES+ 1x10G 10x1G C7600 ES+1x10GE,10x1GE Low queue Combo Link Daughter card

cevC6xxxEsTXc40G  OBJECT IDENTIFIER
    ::= { cevModuleC6xxxType 121 }

-- 7600 ES+ 2x10G 20x1G C7600 ES+2x10GE,20x1GE Low queue Combo Link Daughter card

cevC6xxxEsT8Tg  OBJECT IDENTIFIER
    ::= { cevModuleC6xxxType 122 }

-- 76-ES+T-8TG : 7600 ES+ 8x10G HD Low queue link Daughter card

cevC6xxxEsXt8TG  OBJECT IDENTIFIER
    ::= { cevModuleC6xxxType 123 }

-- 7600 ES+ 8x10G HD High-Queue link Daughter card

cevC6xxxIA48FPD  OBJECT IDENTIFIER
    ::= { cevModuleC6xxxType 124 }

-- Catalyst 6800IA 48 Gig Downlinks and 2 SFP+ uplink with support for a 2 x 10G stacking module. POE support for 740W

cevC6xxxIA48TD  OBJECT IDENTIFIER
    ::= { cevModuleC6xxxType 125 }

-- Catalyst 6800IA 48 Gig Downlinks and 2 SFP+ uplink with support for a 2 x 10G stacking module
--   

-- cevModuleGsrType cards are slot-cards specific to the GSR platform

cevModuleGsrType  OBJECT IDENTIFIER
    ::= { cevModule 18 }

cevGsrOc12Chsts3Mm  OBJECT IDENTIFIER
    ::= { cevModuleGsrType 1 }

-- GSR OC12 channelized to STS-3c/STM-1 multi-mode line card

cevGsrOc12Chsts3Sm  OBJECT IDENTIFIER
    ::= { cevModuleGsrType 2 }

-- GSR OC12 channelized to STS-3c/STM-1 single-mode line card

cevGsrQoc12Mm  OBJECT IDENTIFIER
    ::= { cevModuleGsrType 3 }

-- GSR Four Port OC12c/STM-4c Multi-mode ATM Card

cevGsrQoc12Sm  OBJECT IDENTIFIER
    ::= { cevModuleGsrType 4 }

-- GSR Four Port OC12c/STM-4c Single-Mode ATM Card

cevPosOc48SmLrFc  OBJECT IDENTIFIER
    ::= { cevModuleGsrType 5 }

-- GSR 1 Port Packet Over SONET OC-48c/STM-16 Single Mode Long Reach with FC connector

cevPosQoc3SmL  OBJECT IDENTIFIER
    ::= { cevModuleGsrType 6 }

-- GSR Four Port Packet Over SONET OC-3c/STM-1 Single Mode Long Reach

cevPos8oc3Mm  OBJECT IDENTIFIER
    ::= { cevModuleGsrType 7 }

-- GSR 8 port OC3 Multimode POS

cevPos8oc3Ir  OBJECT IDENTIFIER
    ::= { cevModuleGsrType 8 }

-- GSR 8 port OC3 SM intermediate reach POS

cevPos8oc3Lr  OBJECT IDENTIFIER
    ::= { cevModuleGsrType 9 }

-- GSR 8 port OC3 SM long reach POS

cevPos16oc3Mm  OBJECT IDENTIFIER
    ::= { cevModuleGsrType 10 }

-- GSR 16 port OC3 multimode POS

cevPos16oc3Ir  OBJECT IDENTIFIER
    ::= { cevModuleGsrType 11 }

-- GSR 16 port OC3 SM intermediate reach POS

cevPos16oc3Lr  OBJECT IDENTIFIER
    ::= { cevModuleGsrType 12 }

-- GSR 16 port OC3 SM long reach POS

cevGsr8feTx  OBJECT IDENTIFIER
    ::= { cevModuleGsrType 13 }

-- GSR 8 port Fast Ethernet card with copper interface

cevGsr8feFx  OBJECT IDENTIFIER
    ::= { cevModuleGsrType 14 }

-- GSR 8 port Fast Ethernet card with fiber interface

cevSsrpOc48SmSr  OBJECT IDENTIFIER
    ::= { cevModuleGsrType 15 }

-- GSR 1 port SONET based SRP OC-48c/STM-16 Single Mode, Short Reach

cevSsrpOc48SmLr  OBJECT IDENTIFIER
    ::= { cevModuleGsrType 16 }

-- GSR 1 port SONET based SRP OC-48c/STM-16 Single Mode, Long Reach

cevPosQoc12SmLr  OBJECT IDENTIFIER
    ::= { cevModuleGsrType 17 }

-- GSR 4 port (Quad) OC-12 POS cards, single mode, long reach

cevPosQoc12MmSr  OBJECT IDENTIFIER
    ::= { cevModuleGsrType 18 }

-- GSR 4 port (Quad) OC-12 POS cards, multi mode, short reach

cevPosOc48SmSrFc  OBJECT IDENTIFIER
    ::= { cevModuleGsrType 19 }

-- GSR 1 port Packet Over Sonet OC-48 card, single mode, short reach, with FC connector

cevPosOc48SmLrSc  OBJECT IDENTIFIER
    ::= { cevModuleGsrType 20 }

-- GSR 1 port Packet Over Sonet OC-48 card, single mode, long reach, with SC connector

cevPosOc48SmSrSc  OBJECT IDENTIFIER
    ::= { cevModuleGsrType 21 }

-- GSR 1 port Packet Over Sonet OC-48 card, single mode, short reach, with SC connector

cevSrpOc12SmIr  OBJECT IDENTIFIER
    ::= { cevModuleGsrType 22 }

-- GSR 1 port single mode SRP OC-12/STM-4 intermediate reach module

cevSrpOc12SmLr  OBJECT IDENTIFIER
    ::= { cevModuleGsrType 23 }

-- GSR 1 port single mode SRP OC-12/STM-4 long reach module

cevSrpOc12Mm  OBJECT IDENTIFIER
    ::= { cevModuleGsrType 24 }

-- GSR 1 port SRP OC-12/STM-4 Multimode Ring line card

cevPosEnOc48SrSc  OBJECT IDENTIFIER
    ::= { cevModuleGsrType 25 }

-- GSR enhanced OC-48 short reach SC connector line card

cevPosEnOc48SrFc  OBJECT IDENTIFIER
    ::= { cevModuleGsrType 26 }

-- GSR enhanced OC-48 short reach FC connector line card

cevPosEnOc48LrSc  OBJECT IDENTIFIER
    ::= { cevModuleGsrType 27 }

-- GSR enhanced OC-48 long reach SC connector line card

cevPosEnOc48LrFc  OBJECT IDENTIFIER
    ::= { cevModuleGsrType 28 }

-- GSR enhanced OC-48 long reach FC connector line card

cevPosEnQoc12Sr  OBJECT IDENTIFIER
    ::= { cevModuleGsrType 29 }

-- GSR enhanced 4 port OC-12 short reach line card

cevPosEnQoc12Ir  OBJECT IDENTIFIER
    ::= { cevModuleGsrType 30 }

-- GSR enhanced 4 port OC-12 intermediate reach line card

cevCopper6ds3  OBJECT IDENTIFIER
    ::= { cevModuleGsrType 31 }

-- GSR 6 port copper DS3 interface line card

cevCopper12ds3  OBJECT IDENTIFIER
    ::= { cevModuleGsrType 32 }

-- GSR 12 port copper DS3 interface line card

cevPosOc192SmIrFc  OBJECT IDENTIFIER
    ::= { cevModuleGsrType 33 }

-- GSR 1 port Packet Over SONET OC-48c/STM-16 Single Mode Intermediate Reach with FC connector

cevPosOc192SmSrFc  OBJECT IDENTIFIER
    ::= { cevModuleGsrType 34 }

-- GSR 1 port Packet Over SONET OC-48c/STM-16 Single Mode Short Reach with FC connector

cevPosOc192SmIrSc  OBJECT IDENTIFIER
    ::= { cevModuleGsrType 35 }

-- GSR 1 port Packet Over SONET OC-48c/STM-16 Single Mode Intermediate Reach with SC connector

cevPosOc192SmSrSc  OBJECT IDENTIFIER
    ::= { cevModuleGsrType 36 }

-- GSR 1 port Packet Over SONET OC-48c/STM-16 Single Mode Short Reach with SC connector

cevPos4Oc3Mm  OBJECT IDENTIFIER
    ::= { cevModuleGsrType 37 }

-- 4 port OC3 POS multimode linecard

cevPos4Oc3Sm  OBJECT IDENTIFIER
    ::= { cevModuleGsrType 38 }

-- 4 port OC3 POS single mode linecard

cevPosOc12Mm  OBJECT IDENTIFIER
    ::= { cevModuleGsrType 39 }

-- 1 port OC12 POS multimode linecard

cevPosOc12Sm  OBJECT IDENTIFIER
    ::= { cevModuleGsrType 40 }

-- 1 port OC12 POS single mode linecard

cevAtmOc12Mm  OBJECT IDENTIFIER
    ::= { cevModuleGsrType 41 }

-- 1 port OC12 ATM multimode linecard

cevAtmOc12Sm  OBJECT IDENTIFIER
    ::= { cevModuleGsrType 42 }

-- 1 port OC12 ATM singlmode linecard

cevPosOc48MmL  OBJECT IDENTIFIER
    ::= { cevModuleGsrType 43 }

-- 1 port OC48 POS multimode  long reach

cevAtm4Oc3Sm  OBJECT IDENTIFIER
    ::= { cevModuleGsrType 44 }

-- 4 port OC3 ATM single mode linecard

cevAtm4Oc3Mm  OBJECT IDENTIFIER
    ::= { cevModuleGsrType 45 }

-- 4 port OC3 ATM multimode linecard

cevOc12ChDs3Mm  OBJECT IDENTIFIER
    ::= { cevModuleGsrType 46 }

-- OC12 Channelized DS3 multimode linecard

cevOc12ChDs3Sm  OBJECT IDENTIFIER
    ::= { cevModuleGsrType 47 }

-- OC12 Channelized DS3 single mode linecard

cevGsrGe  OBJECT IDENTIFIER
    ::= { cevModuleGsrType 48 }

-- 1 port Gigabit Ethernet line card

cevGsr3ge  OBJECT IDENTIFIER
    ::= { cevModuleGsrType 49 }

-- GSR 3 Port Gigabit Ethernet Line Card

cevGsrAlarm16  OBJECT IDENTIFIER
    ::= { cevModuleGsrType 50 }

-- GSR Alarm Module

cevGsrBusBoard16  OBJECT IDENTIFIER
    ::= { cevModuleGsrType 51 }

-- GSR Bus Board for power distribution

cevSrpOc12SmXr  OBJECT IDENTIFIER
    ::= { cevModuleGsrType 52 }

-- GSR 1 port single mode SRP OC-12/STM-4 extended reach module

cevPosEnQoc12Mm  OBJECT IDENTIFIER
    ::= { cevModuleGsrType 53 }

-- GSR enhanced 4 port OC-12 multimode line card

cevPosEnQoc48SmSrFc  OBJECT IDENTIFIER
    ::= { cevModuleGsrType 54 }

-- GSR enhanced 4 Port Packet Over Sonet OC-48, Single Mode, Short Reach, FC Connector Card

cevPosEnQoc48SmSrSc  OBJECT IDENTIFIER
    ::= { cevModuleGsrType 55 }

-- GSR enhanced 4 Port Packet Over Sonet OC-48, Single Mode, Short Reach, SC Connector Card

cevPosEnQoc48SmLrSc  OBJECT IDENTIFIER
    ::= { cevModuleGsrType 56 }

-- GSR enhanced 4 Port Packet Over Sonet OC-48, Single Mode, Long Reach, SC Connector Card

cevPosEnQoc48SmLrFc  OBJECT IDENTIFIER
    ::= { cevModuleGsrType 57 }

-- GSR enhanced 4 Port Packet Over Sonet OC-48, Single Mode, Long Reach, FC Connector Card

cevGsr6Ct3  OBJECT IDENTIFIER
    ::= { cevModuleGsrType 58 }

-- GSR 6 Port Channelized T3 Line Card

cevPosEnOc192SmLrFc  OBJECT IDENTIFIER
    ::= { cevModuleGsrType 59 }

-- GSR enhanced 1 Port Packet Over Sonet OC-192, Single Mode, Long Reach, FC Connector Card

cevPosEnOc192SmLrSc  OBJECT IDENTIFIER
    ::= { cevModuleGsrType 60 }

-- GSR enhanced 1 Port Packet Over Sonet OC-192, Single Mode, Long Reach, SC Connector Card

cevPosEnOc192SmVsrSc  OBJECT IDENTIFIER
    ::= { cevModuleGsrType 61 }

-- GSR enhanced 1 Port Packet Over Sonet OC-192, Single Mode, Very Short Reach, SC Connector Card

cevPosEnOc192SmVsrFc  OBJECT IDENTIFIER
    ::= { cevModuleGsrType 62 }

-- GSR enhanced 1 Port Packet Over Sonet OC-192, Single Mode, Very Short Reach, FC Connector Card

cevGsrQoc12Chstsds3SmIrSc  OBJECT IDENTIFIER
    ::= { cevModuleGsrType 66 }

-- GSR 4 port OC12 channelized to STS-12c/STM-4, STS-3c/STM1, or DS-3, Single Mode, Intermediate Reach and SC connector line card

cevGsrQoc12Chstsds3MmSrSc  OBJECT IDENTIFIER
    ::= { cevModuleGsrType 67 }

-- GSR 4 port OC12 channelized to STS-12c/STM-4, STS-3c/STM1, or DS-3, Multi Mode, Short Reach and SC connector line card

cevGsrOc48Chstsds3MmSrSc  OBJECT IDENTIFIER
    ::= { cevModuleGsrType 68 }

-- GSR 1 port OC48 channelized to STS-48c/STM16, STS-12c/STM-4, STS-3c/STM1 or DS-3, Multi Mode, Short Reach  and SC  connector line card

cevGsrOc48Chstsds3SmIrSc  OBJECT IDENTIFIER
    ::= { cevModuleGsrType 69 }

-- GSR 1 port OC48 channelized to STS-48c/STM16, STS-12c/STM-4, STS-3c/STM1 or DS-3, Single Mode, Intermediate Reach and SC connector line card

cevGsrOc48Chstsds3SmLrSc  OBJECT IDENTIFIER
    ::= { cevModuleGsrType 70 }

-- GSR 1 port OC48 channelized to STS-48c/STM16, STS-12c/STM-4, STS-3c/STM1 or DS-3, Single Mode, Long Reach and SC connector line card

cevGsr16Oc3Chstsds3MmSrSc  OBJECT IDENTIFIER
    ::= { cevModuleGsrType 71 }

-- GSR 16 port OC3 channelized to STS-3c/STM-1 or DS-3; Multi Mode fiber, Short Reach, SC connector line card

cevGsr16Oc3Chstsds3SmIrSc  OBJECT IDENTIFIER
    ::= { cevModuleGsrType 72 }

-- GSR 16 port OC3 channelized to STS-3c/STM-1 or DS-3; Single Mode fiber, Intermediate Reach, SC connector line card

cevGsr16Oc3Chstsds3SmLrSc  OBJECT IDENTIFIER
    ::= { cevModuleGsrType 73 }

-- GSR 16 port OC3 channelized to STS-3c/STM-1 or DS-3; Single Mode fiber, Long Reach, SC connector line card

cevGsr2Oc3ChDs1  OBJECT IDENTIFIER
    ::= { cevModuleGsrType 74 }

-- GSR platform card, 2 ports of OC3 (Sonet/SDH); each port is channelized to DS1 level

cevSsrpOc192SmLr  OBJECT IDENTIFIER
    ::= { cevModuleGsrType 75 }

-- GSR 1 port SONET based SRP OC-192c/STM-64 single mode long reach line card

cevSsrpOc192SmIr  OBJECT IDENTIFIER
    ::= { cevModuleGsrType 76 }

-- GSR 1 port SONET based SRP OC-192c/STM-64 single mode intermediate reach line card

cevSsrpOc192SmSr  OBJECT IDENTIFIER
    ::= { cevModuleGsrType 77 }

-- GSR 1 port SONET based SRP OC-192c/STM-64 single mode short reach line card

cevSsrpOc192SmVsr  OBJECT IDENTIFIER
    ::= { cevModuleGsrType 78 }

-- GSR 1 port SONET based SRP OC-192c/STM-64 single mode very short reach line card

cev2Oc12ChDs3Sm  OBJECT IDENTIFIER
    ::= { cevModuleGsrType 80 }

-- Two Port OC12 Channelized ds3 single mode linecard

cevGsrAlarm10  OBJECT IDENTIFIER
    ::= { cevModuleGsrType 81 }

-- GSR Alarm module

cevGsrBusBoard10  OBJECT IDENTIFIER
    ::= { cevModuleGsrType 82 }

-- GSR Bus Board for Power distribution

cevGsrOc48Chstsds3SmSrSc  OBJECT IDENTIFIER
    ::= { cevModuleGsrType 83 }

-- GSR 1-port-OC48, channelized to STS-48c/STM-16, STS-12c/STM-4, STS-3c/STM-1 or DS3, single mode, short-reach, SC connector

cevGsrE48PosOc48SmSrSc  OBJECT IDENTIFIER
    ::= { cevModuleGsrType 84 }

-- GSR, Edge Engine 48, (concatenated) 1 port OC48 POS, single mode, short-reach, SC connector

cevGsrE48PosOc48SmLrSc  OBJECT IDENTIFIER
    ::= { cevModuleGsrType 85 }

-- GSR, Edge Engine 48, (concatenated) 1 port OC48 POS, single mode, long-reach, SC connector

cevGsrE48PosQoc12SmIrSc  OBJECT IDENTIFIER
    ::= { cevModuleGsrType 86 }

-- GSR, Edge Engine 48, 4 port (concatenated) OC12 POS, single mode, intermediate reach, SC connector

cevGsrE48Pos16oc3SmIrSc  OBJECT IDENTIFIER
    ::= { cevModuleGsrType 87 }

-- GSR, Edge Engine 48, 16 port (concatenated) OC3 POS, single mode, intermediate reach, SC connector

cevCopper6e3  OBJECT IDENTIFIER
    ::= { cevModuleGsrType 88 }

-- GSR 6 port copper E3 interface line card

cevCopper12e3  OBJECT IDENTIFIER
    ::= { cevModuleGsrType 89 }

-- GSR 12 port copper E3 interface line card

cevGsrE48Pos16oc3SmIrLc  OBJECT IDENTIFIER
    ::= { cevModuleGsrType 93 }

-- GSR, Edge Engine 48, 16 port (concatenated) OC3 POS, single mode, intermediate reach, LC connector

cevGsr16oc3Chstsds3SmIrLc  OBJECT IDENTIFIER
    ::= { cevModuleGsrType 94 }

-- GSR 16 port OC3 channelized to STS-3c/STM-1 or DS-3; single mode fiber, intermediate reach, LC connector

cevGsrOc12ChDs1SmIrSc  OBJECT IDENTIFIER
    ::= { cevModuleGsrType 95 }

-- GSR 1 port OC12 channelized to DS1, single-mode intermediate reach line card with SC connector

cevGsrAlarm6  OBJECT IDENTIFIER
    ::= { cevModuleGsrType 96 }

-- GSR 12406 Alarm Module

cevPosEnQoc48Vsr  OBJECT IDENTIFIER
    ::= { cevModuleGsrType 97 }

-- GSR enhanced 4 Port Packet Over Sonet OC-48, Very Short Reach Card

cevPosEnQoc48MmSrSc  OBJECT IDENTIFIER
    ::= { cevModuleGsrType 98 }

-- GSR enhanced 4 Port Packet Over Sonet OC-48, Multi Mode, Short Reach, SC Connector Card

cevPosEnQoc48SmIrSc  OBJECT IDENTIFIER
    ::= { cevModuleGsrType 99 }

-- GSR enhanced 4 Port Packet Over Sonet OC-48, Single Mode, Intermediate Reach, SC Connector Card

cevPosEnQoc48SmIrFc  OBJECT IDENTIFIER
    ::= { cevModuleGsrType 100 }

-- GSR enhanced 4 Port Packet Over Sonet OC-48, Single Mode, Intermediate Reach, FC Connector Card

cevPosEnQoc48SmVlrSc  OBJECT IDENTIFIER
    ::= { cevModuleGsrType 101 }

-- GSR enhanced 4 Port Packet Over Sonet OC-48, Single Mode, Very Long Reach, SC Connector Card

cevPosEnQoc48SmVlrFc  OBJECT IDENTIFIER
    ::= { cevModuleGsrType 102 }

-- GSR enhanced 4 Port Packet Over Sonet OC-48, Single Mode, Very Long Reach, FC Connector Card

cevPosEnQoc48SmElrSc  OBJECT IDENTIFIER
    ::= { cevModuleGsrType 103 }

-- GSR enhanced 4 Port Packet Over Sonet OC-48, Single Mode, Extremely Long Reach, SC Connector Card

cevPosEnQoc48SmElrFc  OBJECT IDENTIFIER
    ::= { cevModuleGsrType 104 }

-- GSR enhanced 4 Port Packet Over Sonet OC-48, Single Mode, Extremely Long Reach, FC Connector Card

cevPosEnOc192Vsr  OBJECT IDENTIFIER
    ::= { cevModuleGsrType 105 }

-- GSR enhanced 1 Port Packet Over Sonet OC-192, Very Short Reach Card

cevPosEnOc192SmSr2Sc  OBJECT IDENTIFIER
    ::= { cevModuleGsrType 106 }

-- GSR enhanced 1 Port Packet Over Sonet OC-192, Single Mode, Short Reach 2, SC Connector Card

cevPosEnOc192SmSr2Fc  OBJECT IDENTIFIER
    ::= { cevModuleGsrType 107 }

-- GSR enhanced 1 Port Packet Over Sonet OC-192, Single Mode, Short Reach 2, FC Connector Card

cevPosEnOc192SmVlrSc  OBJECT IDENTIFIER
    ::= { cevModuleGsrType 108 }

-- GSR enhanced 1 Port Packet Over Sonet OC-192, Single Mode, Very Long Reach, SC Connector Card

cevPosEnOc192SmVlrFc  OBJECT IDENTIFIER
    ::= { cevModuleGsrType 109 }

-- GSR enhanced 1 Port Packet Over Sonet OC-192, Single Mode, Very Long Reach, FC Connector Card

cevPosEnOc192SmElrSc  OBJECT IDENTIFIER
    ::= { cevModuleGsrType 110 }

-- GSR enhanced 1 Port Packet Over Sonet OC-192, Single Mode, Extremely Long Reach, SC Connector Card

cevPosEnOc192SmElrFc  OBJECT IDENTIFIER
    ::= { cevModuleGsrType 111 }

-- GSR enhanced 1 Port Packet Over Sonet OC-192, Single Mode, Extremely Long Reach, FC Connector Card

cevGsrEn8Oc3  OBJECT IDENTIFIER
    ::= { cevModuleGsrType 112 }

-- GSR enhanced 8 port OC3c/STM-1 ATM LC

cevGsr1p10ge  OBJECT IDENTIFIER
    ::= { cevModuleGsrType 113 }

-- One Port 10 Gigabit Ethernet Card for the 12000 series routers

cevGsrE48PosOc48SmIrSc  OBJECT IDENTIFIER
    ::= { cevModuleGsrType 114 }

-- GSR, Edge Engine, OC48 POS, Single Mode, Intermediate Reach, SC Connector

cevGsrEOc192SmLrSc  OBJECT IDENTIFIER
    ::= { cevModuleGsrType 116 }

-- GSR Edge 1 Port Packet over Sonet OC-192, Single Mode, Long Reach, SC Connector card

cevGsrEOc192SmVsrSc  OBJECT IDENTIFIER
    ::= { cevModuleGsrType 117 }

-- GSR Edge 1 Port Packet over Sonet OC-192, Single Mode, Very Short Reach, SC Connector card

cevGsrEOc192SmVsrFc  OBJECT IDENTIFIER
    ::= { cevModuleGsrType 118 }

-- GSR Edge 1 Port Packet over Sonet OC-192, Single Mode, Very Short Reach, FC Connector card

cevGsrEOc192SmSrFc  OBJECT IDENTIFIER
    ::= { cevModuleGsrType 119 }

-- GSR Edge 1 Port Packet over Sonet OC-192, Single Mode, Short Reach, FC Connector card

cevGsrEOc192SmSrSc  OBJECT IDENTIFIER
    ::= { cevModuleGsrType 120 }

-- GSR Edge 1 Port Packet over Sonet OC-192, Single Mode, Short Reach, SC Connector card

cevGsrEOc192SmLrFc  OBJECT IDENTIFIER
    ::= { cevModuleGsrType 121 }

-- GSR Edge 1 Port Packet over Sonet OC-192, Single Mode, Long Reach, FC Connector card

cevGsrEQoc48SmLrFc  OBJECT IDENTIFIER
    ::= { cevModuleGsrType 122 }

-- GSR Edge 4 Port Packet over Sonet OC-48, Single Mode, Long Reach, FC Connector card

cevGsrEQoc48SmLrSc  OBJECT IDENTIFIER
    ::= { cevModuleGsrType 123 }

-- GSR Edge 4 Port Packet over Sonet OC-48, Single Mode, Long Reach, SC Connector card

cevGsrEQoc48SmVsrSc  OBJECT IDENTIFIER
    ::= { cevModuleGsrType 124 }

-- GSR Edge 4 Port Packet over Sonet OC-48, Single Mode, Very Short Reach, SC Connector card

cevGsrEQoc48SmVsrFc  OBJECT IDENTIFIER
    ::= { cevModuleGsrType 125 }

-- GSR Edge 4 Port Packet over Sonet OC-48, Single Mode, Very Short Reach, FC Connector card

cevGsrEQoc48SmSrFc  OBJECT IDENTIFIER
    ::= { cevModuleGsrType 126 }

-- GSR Edge 4 Port Packet over Sonet OC-48, Single Mode, Short Reach, FC Connector card

cevGsrEQoc48SmSrSc  OBJECT IDENTIFIER
    ::= { cevModuleGsrType 127 }

-- GSR Edge 4 Port Packet over Sonet OC-48, Single Mode, Short Reach, SC Connector card

cevGsrEQoc48Vsr  OBJECT IDENTIFIER
    ::= { cevModuleGsrType 128 }

-- GSR Edge 4 Port Packet over Sonet OC-48, Very Short Reach

cevGsrEQoc48SmSr2Sc  OBJECT IDENTIFIER
    ::= { cevModuleGsrType 129 }

-- GSR Edge 4 Port Packet over Sonet OC-48, Single Mode, Short Reach 2, SC Connector card

cevGsrEQoc48SmSr2Fc  OBJECT IDENTIFIER
    ::= { cevModuleGsrType 130 }

-- GSR Edge 4 Port Packet over Sonet OC-48, Single Mode, Short Reach 2, FC Connector card

cevGsrEQoc48MmSrSc  OBJECT IDENTIFIER
    ::= { cevModuleGsrType 131 }

-- GSR Edge 4 Port Packet over Sonet OC-48, Multi Mode, Short Reach, SC Connector card

cevGsrEQoc48SmIrSc  OBJECT IDENTIFIER
    ::= { cevModuleGsrType 132 }

-- GSR Edge 4 Port Packet over Sonet OC-48, Single Mode, Intermediate Reach, SC Connector card

cevGsrEQoc48SmIrFc  OBJECT IDENTIFIER
    ::= { cevModuleGsrType 133 }

-- GSR Edge 4 Port Packet over Sonet OC-48, Single Mode, Intermediate Reach, FC Connector card

cevGsrEQoc48SmVlrSc  OBJECT IDENTIFIER
    ::= { cevModuleGsrType 134 }

-- GSR Edge 4 Port Packet over Sonet OC-48, Single Mode, Very Long Reach, SC Connector card

cevGsrEQoc48SmVlrFc  OBJECT IDENTIFIER
    ::= { cevModuleGsrType 135 }

-- GSR Edge 4 Port Packet over Sonet OC-48, Single Mode, Very Long Reach, FC Connector card

cevGsrEQoc48SmElrSc  OBJECT IDENTIFIER
    ::= { cevModuleGsrType 136 }

-- GSR Edge 4 Port Packet over Sonet OC-48, Single Mode, Extremely Long Reach, SC Connector card

cevGsrEQoc48SmElrFc  OBJECT IDENTIFIER
    ::= { cevModuleGsrType 137 }

-- GSR Edge 4 Port Packet over Sonet OC-48, Single Mode, Extremely Long Reach, FC Connector card

cevGsrEOc192Vsr  OBJECT IDENTIFIER
    ::= { cevModuleGsrType 138 }

-- GSR Edge 1 Port Packet over Sonet OC-192, Very Short Reach

cevGsrEOc192SmSr2Sc  OBJECT IDENTIFIER
    ::= { cevModuleGsrType 139 }

-- GSR Edge 1 Port Packet over Sonet OC-192, Single Mode, Short Reach 2, SC Connector card

cevGsrEOc192SmSr2Fc  OBJECT IDENTIFIER
    ::= { cevModuleGsrType 140 }

-- GSR Edge 1 Port Packet over Sonet OC-192, Single Mode, Short Reach 2, FC Connector card

cevGsrEOc192MmSrSc  OBJECT IDENTIFIER
    ::= { cevModuleGsrType 141 }

-- GSR Edge 1 Port Packet over Sonet OC-192, Multi Mode, Short Reach, SC Connector card

cevGsrEOc192SmIrSc  OBJECT IDENTIFIER
    ::= { cevModuleGsrType 142 }

-- GSR Edge 1 Port Packet over Sonet OC-192, Single Mode, Intermediate Reach, SC Connector card

cevGsrEOc192SmIrFc  OBJECT IDENTIFIER
    ::= { cevModuleGsrType 143 }

-- GSR Edge 1 Port Packet over Sonet OC-192, Single Mode, Intermediate Reach, FC Connector card

cevGsrEOc192SmVlrSc  OBJECT IDENTIFIER
    ::= { cevModuleGsrType 144 }

-- GSR Edge 1 Port Packet over Sonet OC-192, Single Mode, Very Long Reach, SC Connector card

cevGsrEOc192SmVlrFc  OBJECT IDENTIFIER
    ::= { cevModuleGsrType 145 }

-- GSR Edge 1 Port Packet over Sonet OC-192, Single Mode, Very Long Reach, FC Connector card

cevGsrEOc192SmElrSc  OBJECT IDENTIFIER
    ::= { cevModuleGsrType 146 }

-- GSR Edge 1 Port Packet over Sonet OC-192, Single Mode, Extremely Long Reach, SC Connector card

cevGsrEOc192SmElrFc  OBJECT IDENTIFIER
    ::= { cevModuleGsrType 147 }

-- GSR Edge 1 Port Packet over Sonet OC-192, Single Mode, Extremely Long Reach, FC Connector card

cevSsrp2Oc48SrpSmSrLc  OBJECT IDENTIFIER
    ::= { cevModuleGsrType 148 }

-- GSR 2 port SONET dual SRP/POS OC-48c/STM-16, SRP Mode, Single Mode, Short Reach, LC Connector card

cevSsrp2Oc48SrpSmIrLc  OBJECT IDENTIFIER
    ::= { cevModuleGsrType 149 }

-- GSR 2 port SONET dual SRP/POS OC-48c/STM-16, SRP Mode, Single Mode, Intermediate Reach, LC Connector card

cevSsrp2Oc48SrpSmLrLc  OBJECT IDENTIFIER
    ::= { cevModuleGsrType 150 }

-- GSR 2 port SONET dual SRP/POS OC-48c/STM-16, SRP Mode, Single Mode, Long Reach, LC Connector card

cevSsrp2Oc48PosSmSrLc  OBJECT IDENTIFIER
    ::= { cevModuleGsrType 151 }

-- GSR 2 port SONET dual SRP/POS OC-48c/STM-16, POS Mode, Single Mode, Short Reach, LC Connector card

cevSsrp2Oc48PosSmIrLc  OBJECT IDENTIFIER
    ::= { cevModuleGsrType 152 }

-- GSR 2 port SONET dual SRP/POS OC-48c/STM-16, POS Mode, Single Mode, Intermediate Reach, LC Connector card

cevSsrp2Oc48PosSmLrLc  OBJECT IDENTIFIER
    ::= { cevModuleGsrType 153 }

-- GSR 2 port SONET dual SRP/POS OC-48c/STM-16, POS Mode, Single Mode, Long Reach, LC Connector card

cevGsrE48PosQoc12MmSrSc  OBJECT IDENTIFIER
    ::= { cevModuleGsrType 155 }

-- GSR edge48 Quad OC-12 (concanenated) POS card, Multi Mode (fiber), Short Reach, SC connector

cevGsrGeFe  OBJECT IDENTIFIER
    ::= { cevModuleGsrType 156 }

-- Modular Gigabit/Fast Ethernet card for GSR

cevGsrE48Atm4oc12SmIrSc  OBJECT IDENTIFIER
    ::= { cevModuleGsrType 157 }

-- Edge Engine 48, ATM, 4 ports OC12/STM4, Single Mode, Intermediate Reach, SC connector

cevGsrE48Atm4oc12MmSrSc  OBJECT IDENTIFIER
    ::= { cevModuleGsrType 158 }

-- GSR, Edge Engine 48, ATM, 4 ports OC12/STM4, Multi Mode, Short Reach, SC connector

cevGsrE48Atm4oc3SmIrSc  OBJECT IDENTIFIER
    ::= { cevModuleGsrType 159 }

-- GSR, Edge Engine 48, ATM, 4 ports OC3/STM1, Single Mode, Intermediate reach, SC connector

cevGsrE48Atm4oc3MmSrSc  OBJECT IDENTIFIER
    ::= { cevModuleGsrType 160 }

-- GSR, Edge Engine 48, ATM, 4 ports OC3/STM1, Multi Mode, Short Reach, SC connector

cevGsrE48Pos4oc3SmIrLc  OBJECT IDENTIFIER
    ::= { cevModuleGsrType 162 }

-- GSR, Edge Engine 48, 4 port concatenated OC3 POS, Single mode, Intermediate reach, LC connector

cevGsrE48Pos8oc3SmIrLc  OBJECT IDENTIFIER
    ::= { cevModuleGsrType 166 }

-- GSR, Edge Engine 48, 8 port concatenated OC3 POS, Single mode, Intermediate reach, LC connector

cevSsrp2Oc12E48SmIr  OBJECT IDENTIFIER
    ::= { cevModuleGsrType 167 }

-- GSR 2 port SONET based SRP OC-12c/STM-4 Single mode Intermediate reach line card

cevSsrp2Oc12E48SmXr  OBJECT IDENTIFIER
    ::= { cevModuleGsrType 168 }

-- GSR 2 port SONET based SRP OC-12c/STM-4 Single mode Extented reach line card

cevSsrp1Oc12E48SmIr  OBJECT IDENTIFIER
    ::= { cevModuleGsrType 169 }

-- GSR 1 port SONET based SRP OC-12c/STM-4 Single mode Intermediate reach line card

cevSsrp1Oc12E48SmXr  OBJECT IDENTIFIER
    ::= { cevModuleGsrType 170 }

-- GSR 1 port SONET based SRP OC-12c/STM-4 Single mode Extented reach line card

cevGsrSIP600  OBJECT IDENTIFIER
    ::= { cevModuleGsrType 171 }

-- ISE 10G SPA Interface Card

cevGsr4pge  OBJECT IDENTIFIER
    ::= { cevModuleGsrType 173 }

-- Tetra card Edge engine 3 - 4 port Gigabit Ethernet card

cevGsrAtmEn8Oc3Mm  OBJECT IDENTIFIER
    ::= { cevModuleGsrType 174 }

-- GSR enhanced 8 port OC3c/STM-1 Multimode ATM LC

cevGsr2Oc192Pos  OBJECT IDENTIFIER
    ::= { cevModuleGsrType 175 }

-- GSR 2 Port Packet Over Sonet OC-192c/STM-64 line card

cevGsr8Oc48Pos  OBJECT IDENTIFIER
    ::= { cevModuleGsrType 176 }

-- GSR 8 Port Packet Over Sonet OC-48c/STM-16 line card

cevGsrOc48Msr  OBJECT IDENTIFIER
    ::= { cevModuleGsrType 177 }

-- Cisco 12000 Series 2.5G Modular Services Card

cevPosE2Oc192Vsr  OBJECT IDENTIFIER
    ::= { cevModuleGsrType 178 }

-- GSR Edge 2 Port Packet Over Sonet OC-192, Very Short Reach Card

cevPosE2Oc192SmSr2Sc  OBJECT IDENTIFIER
    ::= { cevModuleGsrType 179 }

-- GSR Edge 2 Port Packet Over Sonet OC-192, Single Mode, Short Reach 2, SC Connector Card

cevPosE2Oc192SmSr2Fc  OBJECT IDENTIFIER
    ::= { cevModuleGsrType 180 }

-- GSR Edge 2 Port Packet Over Sonet OC-192, Single Mode, Short Reach 2, FC Connector Card

cevPosE2Oc192SmSrSc  OBJECT IDENTIFIER
    ::= { cevModuleGsrType 181 }

-- GSR Edge 2 Port Packet Over Sonet OC-192, Single Mode, Short Reach with SC connector

cevPosE2Oc192SmSrFc  OBJECT IDENTIFIER
    ::= { cevModuleGsrType 182 }

-- GSR Edge 2 Port Packet Over Sonet OC-192, Single Mode, Short Reach with FC connector

cevPosE2Oc192SmIrSc  OBJECT IDENTIFIER
    ::= { cevModuleGsrType 183 }

-- GSR Edge 2 port Packet Over SONET OC-192, Single Mode, Intermediate Reach with SC connector

cevPosE2Oc192SmIrFc  OBJECT IDENTIFIER
    ::= { cevModuleGsrType 184 }

-- GSR Edge 2 port Packet Over SONET OC-192, Single Mode, Intermediate Reach with FC connector

cevPosE2Oc192SmLrSc  OBJECT IDENTIFIER
    ::= { cevModuleGsrType 185 }

-- GSR Edge 2 Port Packet Over Sonet OC-192, Single Mode, Long Reach, SC Connector Card

cevPosE2Oc192SmLrFc  OBJECT IDENTIFIER
    ::= { cevModuleGsrType 186 }

-- GSR Edge 2 Port Packet Over Sonet OC-192, Single Mode, Long Reach, FC Connector Card

cevPosE2Oc192SmVlrSc  OBJECT IDENTIFIER
    ::= { cevModuleGsrType 187 }

-- GSR Edge 2 Port Packet Over Sonet OC-192, Single Mode, Very Long Reach, SC Connector Card

cevPosE2Oc192SmVlrFc  OBJECT IDENTIFIER
    ::= { cevModuleGsrType 188 }

-- GSR Edge 2 Port Packet Over Sonet OC-192, Single Mode, Very Long Reach, FC Connector Card

cevPosE2Oc192SmElrSc  OBJECT IDENTIFIER
    ::= { cevModuleGsrType 189 }

-- GSR Edge 2 Port Packet Over Sonet OC-192, Single Mode, Extremely Long Reach, SC Connector Card

cevPosE2Oc192SmElrFc  OBJECT IDENTIFIER
    ::= { cevModuleGsrType 190 }

-- GSR Edge 2 Port Packet Over Sonet OC-192, Single Mode, Extremely Long Reach, FC Connector Card

cevGsr6Ds3e3Smb  OBJECT IDENTIFIER
    ::= { cevModuleGsrType 191 }

-- GSR 6 Port DS3/E3 Clear Channel, SMB Connector line card

cevGsr6Ds3e3Ct3Smb  OBJECT IDENTIFIER
    ::= { cevModuleGsrType 192 }

-- GSR 6 Port DS3/E3 Clear channel and/or Channelized to DS1/E1, SMB Connector line card

cevGsr2Oc3Chds1ds3e3SmIrSc  OBJECT IDENTIFIER
    ::= { cevModuleGsrType 193 }

-- GSR 2 Port STM-1/OC-3 Channelized to DS3/E3/DS1/E1, Single Mode, Intermediate Reach and SC Connector line card

cevGsrService  OBJECT IDENTIFIER
    ::= { cevModuleGsrType 194 }

-- GSR Service Card

cevGsrSIP601  OBJECT IDENTIFIER
    ::= { cevModuleGsrType 195 }

-- ISE 10G SPA Interface Card

cevGsrSIP501  OBJECT IDENTIFIER
    ::= { cevModuleGsrType 196 }

-- ISE 5G SPA Interface Card

cevGsrSIP401  OBJECT IDENTIFIER
    ::= { cevModuleGsrType 197 }

-- ISE 2.5G SPA Interface Card

cevGsrSsrp2Oc48Lc  OBJECT IDENTIFIER
    ::= { cevModuleGsrType 198 }

-- GSR 2 port SONET based SRP OC-48c/STM-16 (SFP) LC

cevGsrE384Cec  OBJECT IDENTIFIER
    ::= { cevModuleGsrType 200 }

-- Cisco 12000 Series SPA nterface Processor-701
--   
-- cevModuleRpmType cards are slot-cards specific to the RPM platform

cevModuleRpmType  OBJECT IDENTIFIER
    ::= { cevModule 19 }

cevAtmdxRpm  OBJECT IDENTIFIER
    ::= { cevModuleRpmType 1 }

-- RPM Cell Bus Interface
--   
-- cevModuleCat8500Type cards are slot cards specific to the Catalyst 85xx MSR/CSR family

cevModuleCat8500Type  OBJECT IDENTIFIER
    ::= { cevModule 20 }

cevCat8500CpuSwitch  OBJECT IDENTIFIER
    ::= { cevModuleCat8500Type 1 }

-- Switch Processor

cevCat8500FeatureFpga  OBJECT IDENTIFIER
    ::= { cevModuleCat8500Type 2 }

-- FPGA feature card

cevCat8500FeatureAsic  OBJECT IDENTIFIER
    ::= { cevModuleCat8500Type 3 }

-- ASIC feature card

cevCat8500FeaturePVC  OBJECT IDENTIFIER
    ::= { cevModuleCat8500Type 4 }

-- PVC feature card

cevCat8500FeUTP8p16k  OBJECT IDENTIFIER
    ::= { cevModuleCat8500Type 5 }

-- 8 port 16k memory fast ethernet UTP card

cevCat8500FeUTP8p64k  OBJECT IDENTIFIER
    ::= { cevModuleCat8500Type 6 }

-- 8 port 64k memory fast ethernet UTP card

cevCat8500FeMMF8p16k  OBJECT IDENTIFIER
    ::= { cevModuleCat8500Type 7 }

-- 8 port 16k memory fast ethernet fiber card

cevCat8500FeMMF8p64k  OBJECT IDENTIFIER
    ::= { cevModuleCat8500Type 8 }

-- 8 port 64k memory fast ethernet fiber card

cevCat8500FeUTP16p16k  OBJECT IDENTIFIER
    ::= { cevModuleCat8500Type 9 }

-- 16 port 16k memory fast ethernet UTP card

cevCat8500FeUTP16p64k  OBJECT IDENTIFIER
    ::= { cevModuleCat8500Type 10 }

-- 16 port 64k memory fast ethernet UTP card

cevCat8500FeMMF16p16k  OBJECT IDENTIFIER
    ::= { cevModuleCat8500Type 11 }

-- 16 port 16k memory fast ethernet fiber card

cevCat8500FeMMF16p64k  OBJECT IDENTIFIER
    ::= { cevModuleCat8500Type 12 }

-- 16 port 64k memory fast ethernet fiber card

cevCat8500GeF1p16k  OBJECT IDENTIFIER
    ::= { cevModuleCat8500Type 13 }

-- 1 port 16k memory gigabit ethernet fiber card

cevCat8500GeF1p64k  OBJECT IDENTIFIER
    ::= { cevModuleCat8500Type 14 }

-- 1 port 64k memory gigabit ethernet fiber card

cevCat8500GeF2p16k  OBJECT IDENTIFIER
    ::= { cevModuleCat8500Type 15 }

-- 2 port 16k memory gigabit ethernet fiber card

cevCat8500GeF2p64k  OBJECT IDENTIFIER
    ::= { cevModuleCat8500Type 16 }

-- 2 port 64k memory gigabit ethernet fiber card

cevCat8500FeBridge4p  OBJECT IDENTIFIER
    ::= { cevModuleCat8500Type 17 }

-- 4 port fast ethernet bridge card

cevCat8500RouteProc  OBJECT IDENTIFIER
    ::= { cevModuleCat8500Type 18 }

-- Routing Processor

cevCat8500Switch10GProc  OBJECT IDENTIFIER
    ::= { cevModuleCat8500Type 19 }

-- 10G switching processor

cevCat8500FeatureNetClock  OBJECT IDENTIFIER
    ::= { cevModuleCat8500Type 20 }

-- Network Clock feature card

cevCat8500FeatureABR  OBJECT IDENTIFIER
    ::= { cevModuleCat8500Type 21 }

-- ABR relative rate feature card

cevCat8500FeatureLite  OBJECT IDENTIFIER
    ::= { cevModuleCat8500Type 22 }

-- Feature Card for Catalyst8540MSR

cevCat8500m16pOC3Mm  OBJECT IDENTIFIER
    ::= { cevModuleCat8500Type 23 }

-- 16-port OC3 Multimode

cevCat8500m16pOC3Sm  OBJECT IDENTIFIER
    ::= { cevModuleCat8500Type 24 }

-- 16-port OC3 SingleMode

cevCat8500m4pOC12Mm  OBJECT IDENTIFIER
    ::= { cevModuleCat8500Type 25 }

-- 4-port OC12 MultiMode

cevCat8500m4pOC12Sm  OBJECT IDENTIFIER
    ::= { cevModuleCat8500Type 26 }

-- 4-port OC12 SingleMode

cevCat8500m4pOC3Utp5  OBJECT IDENTIFIER
    ::= { cevModuleCat8500Type 27 }

-- 4-port OC3 UTP5

cevCat8500m4pOC3Mixed  OBJECT IDENTIFIER
    ::= { cevModuleCat8500Type 28 }

-- 4-port OC3 mixed

cevCat8500m4pOC3Sm  OBJECT IDENTIFIER
    ::= { cevModuleCat8500Type 29 }

-- 4-port OC3 Singlemode

cevCat8500m4pOC3Mm  OBJECT IDENTIFIER
    ::= { cevModuleCat8500Type 30 }

-- 4-port OC3 Multimode

cevCat8500mATM25  OBJECT IDENTIFIER
    ::= { cevModuleCat8500Type 31 }

-- 25Mbps ATM port adapter module

cevCat8500m4pE3  OBJECT IDENTIFIER
    ::= { cevModuleCat8500Type 32 }

-- Quad E3

cevCat8500m4pDs3  OBJECT IDENTIFIER
    ::= { cevModuleCat8500Type 33 }

-- Quad DS3

cevCat8500mCbr75E1  OBJECT IDENTIFIER
    ::= { cevModuleCat8500Type 34 }

-- Circuit Emulation E1 (75ohm)

cevCat8500mCbr120E1  OBJECT IDENTIFIER
    ::= { cevModuleCat8500Type 35 }

-- Circuit Emulation E1 (120ohm)

cevCat8500mCbrT1  OBJECT IDENTIFIER
    ::= { cevModuleCat8500Type 36 }

-- Circuit Emulation T1

cevCat8500mE1  OBJECT IDENTIFIER
    ::= { cevModuleCat8500Type 37 }

-- E1 ATM

cevCat8500mT1  OBJECT IDENTIFIER
    ::= { cevModuleCat8500Type 38 }

-- T1 ATM

cevCat8500mE1Bnc  OBJECT IDENTIFIER
    ::= { cevModuleCat8500Type 39 }

-- E1 ATM with BNC connector

cevCat8500mE3  OBJECT IDENTIFIER
    ::= { cevModuleCat8500Type 40 }

-- E3 ATM

cevCat8500mDs3  OBJECT IDENTIFIER
    ::= { cevModuleCat8500Type 41 }

-- DS3 ATM

cevCat8500m4pFrCE1  OBJECT IDENTIFIER
    ::= { cevModuleCat8500Type 42 }

-- 4-port Channelized E1, Frame-based

cevCat8500m1pFrCT3  OBJECT IDENTIFIER
    ::= { cevModuleCat8500Type 43 }

-- Channelized T3, Frame-based

cevCat8500GeF8p64k  OBJECT IDENTIFIER
    ::= { cevModuleCat8500Type 44 }

-- 8 port 64k memory Gigabit Ethernet fiber card

cevCat8500mArm1p64k  OBJECT IDENTIFIER
    ::= { cevModuleCat8500Type 45 }

-- 1 port ATM router module with 64K memory

cevCat8500mArm2p64k  OBJECT IDENTIFIER
    ::= { cevModuleCat8500Type 46 }

-- 2 port ATM router module with 64K memory

cevCat8500mOC48c1pSm  OBJECT IDENTIFIER
    ::= { cevModuleCat8500Type 47 }

-- 1 port OC48c Single Mode module

cevCat8500mIma8pT1  OBJECT IDENTIFIER
    ::= { cevModuleCat8500Type 48 }

-- 8 port IMA T1 module

cevCat8500mIma8pE1  OBJECT IDENTIFIER
    ::= { cevModuleCat8500Type 49 }

-- 8 port IMA E1 module

cevCat8500mATM25m4p  OBJECT IDENTIFIER
    ::= { cevModuleCat8500Type 50 }

-- 4 port 25 Mbps ATM adapter module

cevCat8500mOC121pMm  OBJECT IDENTIFIER
    ::= { cevModuleCat8500Type 51 }

-- 1 port OC12 Multi Mode module

cevCat8500mOC121pSm  OBJECT IDENTIFIER
    ::= { cevModuleCat8500Type 52 }

-- 1 port OC12 Single Mode module

cevCat8500m1pOC12Mixed  OBJECT IDENTIFIER
    ::= { cevModuleCat8500Type 53 }

-- 1 port OC12 Mixed Mode module

cevCat8500mFimBridge  OBJECT IDENTIFIER
    ::= { cevModuleCat8500Type 54 }

-- ATM Fabric Integration Bridge module

cevCat8500mFimOC12Mm  OBJECT IDENTIFIER
    ::= { cevModuleCat8500Type 55 }

-- ATM Fabric Integration OC12 Multi Mode port module

cevCat8500Ge1pXpif16k  OBJECT IDENTIFIER
    ::= { cevModuleCat8500Type 56 }

-- 1 port 16k memory gigabit ethernet XPIF PM card

cevCat8500Ge1pXpif64k  OBJECT IDENTIFIER
    ::= { cevModuleCat8500Type 57 }

-- 1 port 64k memory gigabit ethernet XPIF PM card

cevCat8500Ge1pXpif256k  OBJECT IDENTIFIER
    ::= { cevModuleCat8500Type 58 }

-- 1 port 256k memory gigabit ethernet XPIF PM card

cevCat8500Atm1pXpif64kOc12SmIr  OBJECT IDENTIFIER
    ::= { cevModuleCat8500Type 59 }

-- 1 port 64k memory ATM OC12 Single Mode Intermediate Reach XPIF PM card

cevCat8500Atm1pXpif256kOc12SmIr  OBJECT IDENTIFIER
    ::= { cevModuleCat8500Type 60 }

-- 1 port 256k memory ATM OC12 Single Mode Intermediate Reach XPIF PM card

cevCat8500Atm1pXpif64kOc12Mm  OBJECT IDENTIFIER
    ::= { cevModuleCat8500Type 61 }

-- 1 port 64k memory ATM OC12 Multi Mode XPIF PM card

cevCat8500Atm1pXpif256kOc12Mm  OBJECT IDENTIFIER
    ::= { cevModuleCat8500Type 62 }

-- 1 port 256k memory ATM OC12 Multi Mode XPIF PM card

cevCat8500Atm1pXpif64kOc3SmIr  OBJECT IDENTIFIER
    ::= { cevModuleCat8500Type 63 }

-- 1 port 64k memory ATM OC3 Single Mode Intermediate Reach XPIF PM card

cevCat8500Atm1pXpif256kOc3SmIr  OBJECT IDENTIFIER
    ::= { cevModuleCat8500Type 64 }

-- 1 port 256k memory ATM OC3 Single Mode Intermediate Reach XPIF PM card

cevCat8500Atm1pXpif64kOc3Mm  OBJECT IDENTIFIER
    ::= { cevModuleCat8500Type 65 }

-- 1 port 64k memory ATM OC3 Multi Mode XPIF PM card

cevCat8500Atm1pXpif256kOc3Mm  OBJECT IDENTIFIER
    ::= { cevModuleCat8500Type 66 }

-- 1 port 256k memory ATM OC3 Multi Mode XPIF PM card

cevCat8500Pos1pXpif64kOc12SmIr  OBJECT IDENTIFIER
    ::= { cevModuleCat8500Type 67 }

-- 1 port 64k memory POS OC12 Single Mode Intermediate Reach XPIF PM card

cevCat8500Pos1pXpif256kOc12SmIr  OBJECT IDENTIFIER
    ::= { cevModuleCat8500Type 68 }

-- 1 port 256k memory POS OC12 Single Mode Intermediate Reach XPIF PM card

cevCat8500Pos1pXpif64kOc12SmLr  OBJECT IDENTIFIER
    ::= { cevModuleCat8500Type 69 }

-- 1 port 64k memory POS OC12 Single Mode Long Reach XPIF PM card

cevCat8500Pos1pXpif256kOc12SmLr  OBJECT IDENTIFIER
    ::= { cevModuleCat8500Type 70 }

-- 1 port 256k memory POS OC12 Single Mode Long Reach XPIF PM card

cevModuleWASCommonCards  OBJECT IDENTIFIER
    ::= { cevModule 21 }

-- These cards can be used in multiple MGX and IGX series Wide Area Edge Switches, but not necessarily all of them.

cevAusm8t1  OBJECT IDENTIFIER
    ::= { cevModuleWASCommonCards 1 }

-- ATM User Network Interface Service Module with 8 T1 ports

cevAusm8e1  OBJECT IDENTIFIER
    ::= { cevModuleWASCommonCards 2 }

-- ATM User Network Interface Service Module with 8 E1 ports

cevCesm8t1  OBJECT IDENTIFIER
    ::= { cevModuleWASCommonCards 3 }

-- Circuit Emulation Service Module with 8 T1 ports

cevCesm8e1  OBJECT IDENTIFIER
    ::= { cevModuleWASCommonCards 4 }

-- Circuit Emulation Service Module with 8 E1 ports

cevFrsm8t1  OBJECT IDENTIFIER
    ::= { cevModuleWASCommonCards 5 }

-- Frame Relay Service Module with 8 T1 ports

cevFrsm8e1  OBJECT IDENTIFIER
    ::= { cevModuleWASCommonCards 6 }

-- Frame Relay Service Module with 8 E1 ports

cevFrsm4x21  OBJECT IDENTIFIER
    ::= { cevModuleWASCommonCards 7 }

-- Frame Relay Service Module supporting 4 high speed X.21 ports

cevFrsm2hssi  OBJECT IDENTIFIER
    ::= { cevModuleWASCommonCards 8 }

-- Frame Relay Service Module supporting 2 high speed HSSI ports

cevAxsm1Oc48  OBJECT IDENTIFIER
    ::= { cevModuleWASCommonCards 9 }

-- AXSM-1-2488 ATM Switch Service Module(AXSM),1 Port, OC48 compliant

cevAxsm4Oc12  OBJECT IDENTIFIER
    ::= { cevModuleWASCommonCards 10 }

-- AXSM-4-622 ATM Switch Service Module, 4 Port, OC12 Compliant

cevAxsm8Oc3  OBJECT IDENTIFIER
    ::= { cevModuleWASCommonCards 11 }

-- AXSM-8-155 ATM Switch Service Module, 8 Port, OC3 Compliant

cevAxsm16Oc3  OBJECT IDENTIFIER
    ::= { cevModuleWASCommonCards 12 }

-- AXSM-16-155 ATM Switch Service Module, 16 Port OC3 Compliant

cevAxsm16T3E3  OBJECT IDENTIFIER
    ::= { cevModuleWASCommonCards 13 }

-- AXSM-16-T3E3 ATM Switch Service Module, 16 Port T3/E3 Module

cevCesm1t3  OBJECT IDENTIFIER
    ::= { cevModuleWASCommonCards 14 }

-- Circuit Emulation Service Module (CESM) with one T3 port

cevCesm1e3  OBJECT IDENTIFIER
    ::= { cevModuleWASCommonCards 15 }

-- Circuit Emulation Service Module (CESM) with one E3 port

cevVism8t1  OBJECT IDENTIFIER
    ::= { cevModuleWASCommonCards 16 }

-- Voice Interworking Service Module (VISM) with 8 T1 ports

cevVism8e1  OBJECT IDENTIFIER
    ::= { cevModuleWASCommonCards 17 }

-- Voice Interworking Service Module (VISM) with 8 E1 ports

cevMGXRpm  OBJECT IDENTIFIER
    ::= { cevModuleWASCommonCards 18 }

-- MGX8800 Route Processor Module having the functionality of a C7200 router

cevMGXSrm3t3  OBJECT IDENTIFIER
    ::= { cevModuleWASCommonCards 19 }

-- MGX8800 Service Redundancy Module supporting 3 T3 ports on back card, used for providing 1:N redundancy for T1 modules

cevEnhAxsm1oc12  OBJECT IDENTIFIER
    ::= { cevModuleWASCommonCards 20 }

-- AXSM-1-622-E Enhanced ATM Switch Service Module, 1 Port, OC12c/STM-4 compliant

cevEnhAxsm2oc12  OBJECT IDENTIFIER
    ::= { cevModuleWASCommonCards 21 }

-- AXSM-2-622-E Enhanced ATM Switch Service Module, 2 Port, OC12c/STM-4 compliant

cevEnhAxsm4oc3  OBJECT IDENTIFIER
    ::= { cevModuleWASCommonCards 22 }

-- AXSM-4-155-E Enhanced ATM Switch Service Module, 4 Ports, OC3c/STM-1 compliant

cevEnhAxsm8oc3  OBJECT IDENTIFIER
    ::= { cevModuleWASCommonCards 23 }

-- AXSM-8-155-E Enhanced ATM Switch Service Module, 8 Ports, OC3c/STM-1 compliant

cevEnhAxsm4stm1  OBJECT IDENTIFIER
    ::= { cevModuleWASCommonCards 24 }

-- AXSM-4-155-E Enhanced ATM Switch Service Module, 4 Ports, STM-1 Electrical

cevEnhAxsm8stm1  OBJECT IDENTIFIER
    ::= { cevModuleWASCommonCards 25 }

-- AXSM-8-155-E Enhanced ATM Switch Service Module, 8 Ports, STM-1 Electrical

cevEnhAxsm8t3e3  OBJECT IDENTIFIER
    ::= { cevModuleWASCommonCards 26 }

-- Enhanced ATM Switch Service Module, 8 T3/E3 Ports

cevEnhAxsm16t3e3  OBJECT IDENTIFIER
    ::= { cevModuleWASCommonCards 27 }

-- Enhanced ATM Switch Service Module, 16 T3/E3 Ports

cevEnhAxsm8t1  OBJECT IDENTIFIER
    ::= { cevModuleWASCommonCards 28 }

-- Enhanced ATM Switch Service Module, 8 T1 Ports and IMA Support

cevEnhAxsm16t1  OBJECT IDENTIFIER
    ::= { cevModuleWASCommonCards 29 }

-- Enhanced ATM Switch Service Module, 16 T1 Ports and IMA Support

cevEnhAxsm8e1  OBJECT IDENTIFIER
    ::= { cevModuleWASCommonCards 30 }

-- Enhanced ATM Switch Service Module, 8 E1 Ports and IMA Support

cevEnhAxsm16e1  OBJECT IDENTIFIER
    ::= { cevModuleWASCommonCards 31 }

-- Enhanced ATM Switch Service Module, 16 E1 Ports and IMA Support

cevAxsm2oc12  OBJECT IDENTIFIER
    ::= { cevModuleWASCommonCards 32 }

-- AXSM-2-622 ATM Switch Service Module(AXSM), 2 Port OC12 Compliant

cevMGXRpmPr  OBJECT IDENTIFIER
    ::= { cevModuleWASCommonCards 34 }

-- Router Processor Module(RPM) Premium in selected MGX Series

cevFrsm4V35  OBJECT IDENTIFIER
    ::= { cevModuleWASCommonCards 38 }

-- Frame Relay Service Module(FRSM-HS1/B) with 4 V.35 Ports

cevFrsm2Ct3  OBJECT IDENTIFIER
    ::= { cevModuleWASCommonCards 39 }

-- Frame Relay Service Module with 2 Channelized T3 Ports

cevFrsm2t3  OBJECT IDENTIFIER
    ::= { cevModuleWASCommonCards 40 }

-- Frame Relay Service Module with 2 ClearChannel/Subrate T3 Ports

cevFrsm2e3  OBJECT IDENTIFIER
    ::= { cevModuleWASCommonCards 41 }

-- Frame Relay Service Module with 2 ClearChannel/Subrate E3 Ports

cevAusmB8t1  OBJECT IDENTIFIER
    ::= { cevModuleWASCommonCards 42 }

-- ATM UNI Service Module(Version B) with 8 T1 Ports

cevAusmB8e1  OBJECT IDENTIFIER
    ::= { cevModuleWASCommonCards 43 }

-- ATM UNI Service Module(Version B) with 8 E1 Ports

cevVixm4oc12  OBJECT IDENTIFIER
    ::= { cevModuleWASCommonCards 45 }

-- Voice Interworking Switching Module(VIXM) 4 port OC12 card

cevVixm16oc3  OBJECT IDENTIFIER
    ::= { cevModuleWASCommonCards 46 }

-- Voice Interworking Switching Module(VIXM) 16 port OC3 card

cevCesmB8e1  OBJECT IDENTIFIER
    ::= { cevModuleWASCommonCards 49 }

-- Circuit Emulation Service Module B (CESN/B) with 8 E1 ports

cevCesmB8t1  OBJECT IDENTIFIER
    ::= { cevModuleWASCommonCards 50 }

-- Circuit Emulation Service Module B (CESN/B) with 8 T1 ports

cevFrsmC8e1  OBJECT IDENTIFIER
    ::= { cevModuleWASCommonCards 51 }

-- Frame Relay Service Module C (FRSM/C) with 8 E1 ports

cevFrsmC8t1  OBJECT IDENTIFIER
    ::= { cevModuleWASCommonCards 52 }

-- Frame Relay Service Module C (FRSM/C) with 8 T1 ports

cevFrsmB2hssi  OBJECT IDENTIFIER
    ::= { cevModuleWASCommonCards 53 }

-- Frame Relay Service Module B (FRSM/B) with 2 hssi ports

cevFrsmB12In1  OBJECT IDENTIFIER
    ::= { cevModuleWASCommonCards 54 }

-- Frame Relay Service Module B (FRSM/B) with 12 In1

cevHsfr12t3  OBJECT IDENTIFIER
    ::= { cevModuleWASCommonCards 55 }

-- High Speed Frame Relay Service Module with 12 T3 ports

cevHsfr12e3  OBJECT IDENTIFIER
    ::= { cevModuleWASCommonCards 56 }

-- High Speed Frame Relay Service Module with 12 E3 ports

cevFrsm12t3  OBJECT IDENTIFIER
    ::= { cevModuleWASCommonCards 57 }

-- Frame Relay Service Module, 12 T3 ports

cevFrsm12e3  OBJECT IDENTIFIER
    ::= { cevModuleWASCommonCards 58 }

-- Frame Relay Service Module, 12 E3 ports

cevFrsmB2T3  OBJECT IDENTIFIER
    ::= { cevModuleWASCommonCards 59 }

-- Frame Relay Service Module B (FRSM/B) with 2 T3 ports

cevMgxSrme1Sts3  OBJECT IDENTIFIER
    ::= { cevModuleWASCommonCards 60 }

-- MGX88xx Service Redundancy Module E(nhancement) supporting 1 STS port on back card, used for providing 1:N redundancy for STS3

cevMgxSrm3t3NoBc  OBJECT IDENTIFIER
    ::= { cevModuleWASCommonCards 61 }

-- MGX88xx Service Redundancy Module, 3 T3 ports, no backcard

cevMgxSrmeNoBc  OBJECT IDENTIFIER
    ::= { cevModuleWASCommonCards 62 }

-- GX88xx Service Redundancy Module E(nhancement), no backcard

cevAxsmEn16t1e1  OBJECT IDENTIFIER
    ::= { cevModuleWASCommonCards 63 }

-- Enhanced ATM Switch Service Module, 16 T1/E1 ports

cevAxsmEn32t1e1  OBJECT IDENTIFIER
    ::= { cevModuleWASCommonCards 64 }

-- Enhanced ATM Switch Service Module, 32 T1/E1 ports

cevFrsmB2e3  OBJECT IDENTIFIER
    ::= { cevModuleWASCommonCards 66 }

-- Frame Relay Service Module B (FRSM/B) with 2 E3 ports

cevVismPr8t1  OBJECT IDENTIFIER
    ::= { cevModuleWASCommonCards 70 }

-- Voice Interworking Service Module Premium Card (VISM-PR)with 8 T1 ports

cevVismPr8e1  OBJECT IDENTIFIER
    ::= { cevModuleWASCommonCards 71 }

-- Voice Interworking Service Module Premium Card (VISM-PR) with 8 E1 ports

cevMGXSrmE1Oc3  OBJECT IDENTIFIER
    ::= { cevModuleWASCommonCards 72 }

-- Cisco MGX88xx Service Redundancy Module (SRM) Enhancement

cevAxsm2Oc48  OBJECT IDENTIFIER
    ::= { cevModuleWASCommonCards 73 }

-- ATM service Module which supports 2 OC48 ports in MGX8850 or MGX8950 chasis

cevAxsm8Oc12  OBJECT IDENTIFIER
    ::= { cevModuleWASCommonCards 74 }

-- ATM service Module which supports 8 OC12 ports in MGX8850 or MGX8950 chasis

cevVxsm4Oc3  OBJECT IDENTIFIER
    ::= { cevModuleWASCommonCards 81 }

-- voice switch service module, 4 port OC3/STM-1 compliant

cevMGXSrm4Oc3  OBJECT IDENTIFIER
    ::= { cevModuleWASCommonCards 82 }

-- MGX88xx voice service redundancy module, used to providing 1:N redundancy for 4 OC3

cevMpsm8t1e1  OBJECT IDENTIFIER
    ::= { cevModuleWASCommonCards 87 }

-- Multi-Protocol Service Module with 8 T1/E1 Interfaces

cevMpsm8t1Atm  OBJECT IDENTIFIER
    ::= { cevModuleWASCommonCards 88 }

-- Multi-Protocol Service Module with ATM service on 8 T1 Interfaces

cevMpsm8t1Fr  OBJECT IDENTIFIER
    ::= { cevModuleWASCommonCards 89 }

-- Multi-Protocol Service Module with Frame Relay service on 8 T1 Interfaces

cevMpsm8t1Ces  OBJECT IDENTIFIER
    ::= { cevModuleWASCommonCards 90 }

-- Multi-Protocol Service Module with Circuit Emulation service on 8 T1 Interfaces

cevMpsm8e1Atm  OBJECT IDENTIFIER
    ::= { cevModuleWASCommonCards 91 }

-- Multi-Protocol Service Module with ATM service on 8 E1 Interfaces

cevMpsm8e1Fr  OBJECT IDENTIFIER
    ::= { cevModuleWASCommonCards 92 }

-- Multi-Protocol Service Module with Frame Relay service on 8 E1

cevMpsm8e1Ces  OBJECT IDENTIFIER
    ::= { cevModuleWASCommonCards 93 }

-- Multi-Protocol Service Module with Circuit Emulation service on 8 E1 Interfaces

cevMpsm16t1e1  OBJECT IDENTIFIER
    ::= { cevModuleWASCommonCards 94 }

-- Multi-Protocol Service Module with 16 T1/E1 Interfaces

cevMpsm16t1Atm  OBJECT IDENTIFIER
    ::= { cevModuleWASCommonCards 95 }

-- Multi-Protocol Service Module with ATM service on 16 T1 Interfaces

cevMpsm16t1Fr  OBJECT IDENTIFIER
    ::= { cevModuleWASCommonCards 96 }

-- Multi-Protocol Service Module with Frame Relay service on 16 T1 Interfaces

cevMpsm16t1Ces  OBJECT IDENTIFIER
    ::= { cevModuleWASCommonCards 97 }

-- Multi-Protocol Service Module with Circuit Emulation service on 16 T1 Interfaces

cevMpsm16e1Atm  OBJECT IDENTIFIER
    ::= { cevModuleWASCommonCards 98 }

-- Multi-Protocol Service Module with ATM service on 16 E1 Interfaces

cevMpsm16e1Fr  OBJECT IDENTIFIER
    ::= { cevModuleWASCommonCards 99 }

-- Multi-Protocol Service Module with Frame Relay service on 16 E1 Interfaces

cevMpsm16e1Ces  OBJECT IDENTIFIER
    ::= { cevModuleWASCommonCards 100 }

-- Multi-Protocol Service Module with Circuit Emulation service on 16 E1 Interfaces

cevMpsm155t3e3  OBJECT IDENTIFIER
    ::= { cevModuleWASCommonCards 101 }

-- ATM and FR Module Which supports OC3, T3 or E3 channelized or IMA ports.

cevMGXSm  OBJECT IDENTIFIER
    ::= { cevModuleWASCommonCards 102 }

-- Generic type for MGX88xx Service Module[ATM, FR, VOICE, Circuit Emulation]

cevVxsm48t1e1  OBJECT IDENTIFIER
    ::= { cevModuleWASCommonCards 103 }

-- Voice switch service module, 48 T1/E1 ports

cevVxsm3T3E3  OBJECT IDENTIFIER
    ::= { cevModuleWASCommonCards 104 }

-- Voice switch service module, 3 T3/E3 ports

cevVxsm6t3e3  OBJECT IDENTIFIER
    ::= { cevModuleWASCommonCards 105 }

-- Voice switch service module, 6 T3/E3 ports

cevVxsm6t3  OBJECT IDENTIFIER
    ::= { cevModuleWASCommonCards 106 }

-- Voice switch service module, 6 T3 front card type. Voice switch service module, 6 T3 front card type

cevMpsm16t1e1Ppp  OBJECT IDENTIFIER
    ::= { cevModuleWASCommonCards 107 }

-- Multi protocol service module supporting 16 T1/E1 lines and supporting only PPP service

cevMpsm155t3e3Ppp  OBJECT IDENTIFIER
    ::= { cevModuleWASCommonCards 108 }

-- Multi protocol service module having t3/e3/oc3 interfaces and supporitng  only PPP service

cevModule38xxType  OBJECT IDENTIFIER
    ::= { cevModule 22 }

-- These cards are used in the Cisco 3800 and MC3800 series.

cevMc3810Vcm3  OBJECT IDENTIFIER
    ::= { cevModule38xxType 1 }

-- MC3810 Voice Compression Module with 3 DSPs (Digital Signal Processor)

cevMc3810Bvm  OBJECT IDENTIFIER
    ::= { cevModule38xxType 2 }

-- MC3810 Basic Voice Module

cevMc3810AvmFxoUk  OBJECT IDENTIFIER
    ::= { cevModule38xxType 3 }

-- MC3810 Analog Voice Module UK Foreign eXchange Office

cevMc3810AvmFxoGer  OBJECT IDENTIFIER
    ::= { cevModule38xxType 4 }

-- MC3810 Analog Voice Module Germany Foreign eXchange Office

cevMc3810Hcm2  OBJECT IDENTIFIER
    ::= { cevModule38xxType 5 }

-- MC3810 High (Voice) Capacity Module with 2 DSPs (Digital Signal Processor)

cevMc3810Hcm6  OBJECT IDENTIFIER
    ::= { cevModule38xxType 6 }

-- MC3810 High (Voice) Capacity Module with 6 DSPs (Digital Signal Processor)

cevMc3810AvmFxoPr3  OBJECT IDENTIFIER
    ::= { cevModule38xxType 7 }

-- MC3810 Analog Voice Module Singapore or Japan Foreign eXchange Office

cevMc3810AvmFxoPr2  OBJECT IDENTIFIER
    ::= { cevModule38xxType 8 }

-- MC3810 Analog Voice Module Australia or New Zealand Foreign eXchange Office

cevMc3810Vdm  OBJECT IDENTIFIER
    ::= { cevModule38xxType 9 }

-- MC3810 Video Dial-up Module enables MC3810 video call management via ATM signaling Subsystem through RS366 or V.35 interface

cevMc3810ApmFxsDid  OBJECT IDENTIFIER
    ::= { cevModule38xxType 10 }

-- MC3810 Foreign Exchange Station (FXS) Direct Inward Dialing (DID) Analog Personality Module

cevMc3810BvmNtTe  OBJECT IDENTIFIER
    ::= { cevModule38xxType 11 }

-- 4 ports NT or TE BRI Voice Module on MC3810

cevMc3810Hcm1  OBJECT IDENTIFIER
    ::= { cevModule38xxType 12 }

-- High performance compression module for the MC3810 platform equipped with one TI 549 DSP

cevMc3810Hcm3  OBJECT IDENTIFIER
    ::= { cevModule38xxType 13 }

-- High performance compression module for the MC3810 platform equipped with three TI 549 DSPs

cevMc3810Hcm4  OBJECT IDENTIFIER
    ::= { cevModule38xxType 14 }

-- High performance compression module for the MC3810 platform equipped with four TI 549 DSPs

cevMc3810Hcm5  OBJECT IDENTIFIER
    ::= { cevModule38xxType 15 }

-- High performance compression module for the MC3810 platform equipped with five TI 549 DSPs

cevSmSre710K9  OBJECT IDENTIFIER
    ::= { cevModule38xxType 17 }

-- SM-SRE-710-K9: Service Module for Modular and Integrated Services Routers

cevSmSre910K9  OBJECT IDENTIFIER
    ::= { cevModule38xxType 18 }

-- SM-SRE-910-K9: Service Module for Modular and Integrated Services Routers

cevModuleCat29xxType  OBJECT IDENTIFIER
    ::= { cevModule 23 }

-- These are modules that are used in Catalyst 2900 series switches.

cevX2914  OBJECT IDENTIFIER
    ::= { cevModuleCat29xxType 1 }

-- 4 port 10/100BaseTX module

cevX2922  OBJECT IDENTIFIER
    ::= { cevModuleCat29xxType 2 }

-- 2 port 100BaseFX module

cevX2914V  OBJECT IDENTIFIER
    ::= { cevModuleCat29xxType 3 }

-- 4 port 10/100BaseTX ISL module

cevX2922V  OBJECT IDENTIFIER
    ::= { cevModuleCat29xxType 4 }

-- 2 port 100BaseFX ISL module

cevX2924V  OBJECT IDENTIFIER
    ::= { cevModuleCat29xxType 5 }

-- 4 port 100BaseFX module

cevX2951  OBJECT IDENTIFIER
    ::= { cevModuleCat29xxType 6 }

-- ATM UTP module

cevX2961  OBJECT IDENTIFIER
    ::= { cevModuleCat29xxType 7 }

-- ATM MMF module

cevX2971  OBJECT IDENTIFIER
    ::= { cevModuleCat29xxType 8 }

-- ATM SMF-MR module

cevX2972  OBJECT IDENTIFIER
    ::= { cevModuleCat29xxType 9 }

-- ATM SMF-LR module

cevX2931  OBJECT IDENTIFIER
    ::= { cevModuleCat29xxType 10 }

-- GBIC Gigabit module

cevModuleCat297024  OBJECT IDENTIFIER
    ::= { cevModuleCat29xxType 12 }

-- Catalyst 2970 24 Ethernet 10/100/1000 port module.

cevModuleCat297024TS  OBJECT IDENTIFIER
    ::= { cevModuleCat29xxType 13 }

-- Catalyst 2970 24 Ethernet  10/100/1000 ports + 4 Ethernet Gigabit SFP ports module.(SFP: Small Form factor Pluggable)

cevModuleCat297048TS  OBJECT IDENTIFIER
    ::= { cevModuleCat29xxType 14 }

-- Catalyst 2970 48 Ethernet  10/100/1000 ports + 4 Ethernet Gigabit SFP ports module.(SFP: Small Form factor Pluggable)

cevModuleCat296024  OBJECT IDENTIFIER
    ::= { cevModuleCat29xxType 15 }

-- Catalyst 2960 24 10/100 ports + 2 dual purpose Gigabit Ethernet ports module

cevModuleCat296048  OBJECT IDENTIFIER
    ::= { cevModuleCat29xxType 16 }

-- Catalyst 2960 48 10/100 ports + 2 dual purpose Gigabit Ethernet ports module

cevModuleCat2960G24  OBJECT IDENTIFIER
    ::= { cevModuleCat29xxType 17 }

-- Catalyst 2960 24 10/100/1000 ports + 2 dual purpose Gigabit Ethernet ports module

cevModuleCat2960G48  OBJECT IDENTIFIER
    ::= { cevModuleCat29xxType 18 }

-- Catalyst 2960 44 10/100/1000 ports + 4 dual purpose Gigabit Ethernet ports module

cevModuleCat296024TT  OBJECT IDENTIFIER
    ::= { cevModuleCat29xxType 19 }

-- Catalyst 2960 24 10/100 ports + 2 10/100/1000 Ethernet ports module

cevModuleCat296048TT  OBJECT IDENTIFIER
    ::= { cevModuleCat29xxType 20 }

-- Catalyst 2960 48 10/100 ports + 2 10/100/1000 Ethernet ports module

cevModuleCat29608TC  OBJECT IDENTIFIER
    ::= { cevModuleCat29xxType 21 }

-- Catalyst 2960 8 10/100 Ethernet ports + 1 dual purpose Gigabit Ethernet ports

cevModuleCat2960G8TC  OBJECT IDENTIFIER
    ::= { cevModuleCat29xxType 22 }

-- Catalyst 2960 7 10/100/1000 Ethernet ports + 1 dual purpose Gigabit Ethernet ports

cevModuleCat296048TCS  OBJECT IDENTIFIER
    ::= { cevModuleCat29xxType 23 }

-- Catalyst 2960 48 10/100 2T/SFP

cevModuleCat296024TCS  OBJECT IDENTIFIER
    ::= { cevModuleCat29xxType 24 }

-- Catalyst 2960 24 10/100 2T/SFP

cevModuleCat296024S  OBJECT IDENTIFIER
    ::= { cevModuleCat29xxType 25 }

-- Catalyst 2960 24 10/100

cevModuleCat296024PC  OBJECT IDENTIFIER
    ::= { cevModuleCat29xxType 26 }

-- Catalyst 2960 24 10/100 PoE, 2 T/SFP

cevModuleCat296024LT  OBJECT IDENTIFIER
    ::= { cevModuleCat29xxType 27 }

-- Catalyst 2960 24 10/100, 8 PoE, 2 T

cevModuleCat2960PD8TT  OBJECT IDENTIFIER
    ::= { cevModuleCat29xxType 28 }

-- Catalyst 2960 8 10/100, 1 T PD

cevModuleCat291824TT  OBJECT IDENTIFIER
    ::= { cevModuleCat29xxType 29 }

-- Catalyst 2918 24 10/100 + 2 10/100/1000 Ethernet ports module

cevModuleCat291824TC  OBJECT IDENTIFIER
    ::= { cevModuleCat29xxType 30 }

-- Catalyst 2918 24 10/100 + 2 dual purpose Gigabit Ethernet ports module

cevModuleCat291848TT  OBJECT IDENTIFIER
    ::= { cevModuleCat29xxType 31 }

-- Catalyst 2918 48 10/100 + 2 10/100/1000 Ethernet ports module

cevModuleCat291848TC  OBJECT IDENTIFIER
    ::= { cevModuleCat29xxType 32 }

-- Catalyst 2918 48 10/100 + 2 dual purpose Gigabit Ethernet ports module

cevModuleCat296048TTS  OBJECT IDENTIFIER
    ::= { cevModuleCat29xxType 33 }

-- Catalyst 2960 48 10/100 + 2 10/100/1000 Ethernet ports module

cevModuleCat29608TCS  OBJECT IDENTIFIER
    ::= { cevModuleCat29xxType 34 }

-- Catalyst 2960 8 10/100 + 1 dual purpose Gigabit Ethernet port module

cevModuleCat296048PSTL  OBJECT IDENTIFIER
    ::= { cevModuleCat29xxType 35 }

-- Catalyst 2960 48 10/100 Power over Ethernet ports + 2 10/100/1000 Ethernet Ports + 2 SFP fixed configuration Layer 2 Ethernet switch

cevModuleCat296024LCS  OBJECT IDENTIFIER
    ::= { cevModuleCat29xxType 36 }

-- Catalyst 2960 8 10/100 Power over Ethernet ports + 16 10/100 Ethernet ports + 2 dual purpose Gigabit Ethernet ports module

cevModuleCat296024PCS  OBJECT IDENTIFIER
    ::= { cevModuleCat29xxType 37 }

-- Catalyst 2960 24 10/100 Power over Ethernet ports + 2 dual purpose Gigabit Ethernet ports module

cevModuleCat296048PSTS  OBJECT IDENTIFIER
    ::= { cevModuleCat29xxType 38 }

-- Catalyst 2960 48 10/100 Power over Ethernet ports + 2 10/100/1000 Ethernet ports + 2 SFP ports module

cevModuleWsC2960s48tsS  OBJECT IDENTIFIER
    ::= { cevModuleCat29xxType 39 }

-- Catalyst 2960S 48 Gig Downlinks and 2 SFP uplink, Nonstackable module

cevModuleWsC2960s24tsS  OBJECT IDENTIFIER
    ::= { cevModuleCat29xxType 40 }

-- Catalyst 2960S 24 Gig Downlinks and 2 SFP uplink, Nonstackable module

cevModuleWsC2960s48fpdL  OBJECT IDENTIFIER
    ::= { cevModuleCat29xxType 41 }

-- Catalyst 2960S 48 Gig Downlinks and 4 SFP uplink with support for a 2 x 10G stacking module. POE support for 740W

cevModuleWsC2960s48lpdL  OBJECT IDENTIFIER
    ::= { cevModuleCat29xxType 42 }

-- Catalyst 2960S 48 Gig Downlinks and 2 SFP+ uplink with support for a 2 x 10G stacking module. POE support for 370W

cevModuleWsC2960s48tdL  OBJECT IDENTIFIER
    ::= { cevModuleCat29xxType 43 }

-- Catalyst 2960S 48 Gig Downlinks and 2 SFP+ uplink with support for a 2 x 10G stacking module

cevModuleWsC2960s24pdL  OBJECT IDENTIFIER
    ::= { cevModuleCat29xxType 44 }

-- Catalyst 2960S 24 Gig Downlinks and 2 SFP+ uplink with support for a 2 x 10G stacking module. POE support for 370W

cevModuleWsC2960s24tdL  OBJECT IDENTIFIER
    ::= { cevModuleCat29xxType 45 }

-- Catalyst 2960S 24 Gig Downlinks and 2 SFP+ uplink with support for a 2 x 10G stacking module

cevModuleWsC2960s48fpsL  OBJECT IDENTIFIER
    ::= { cevModuleCat29xxType 46 }

-- Catalyst 2960S 48 Gig Downlinks and 4 SFP uplink with support for a 2 x 10G stacking module. POE support for 740W

cevModuleWsC2960s48lpsL  OBJECT IDENTIFIER
    ::= { cevModuleCat29xxType 47 }

-- Catalyst 2960S 48 Gig Downlinks and 4 SFP uplink with support for a 2 x 10G stacking module. POE support for 370W

cevModuleWsC2960s24psL  OBJECT IDENTIFIER
    ::= { cevModuleCat29xxType 48 }

-- Catalyst 2960S 24 Gig Downlinks and 4 SFP uplink with support for a 2 x 10G stacking module. POE support for 370W

cevModuleWsC2960s48tsL  OBJECT IDENTIFIER
    ::= { cevModuleCat29xxType 49 }

-- Catalyst 2960S 48 Gig Downlinks and 4 SFP uplink with support for a 2 x 10G stacking module

cevModuleWsC2960S24tsL  OBJECT IDENTIFIER
    ::= { cevModuleCat29xxType 50 }

-- Catalyst2960S 24 Gig Downlinks and 4 SFP uplink with support for a 2 x 10G stacking module

cevModuleCat2960cPD8TT  OBJECT IDENTIFIER
    ::= { cevModuleCat29xxType 51 }

-- Catalyst 2960c  8 10/100 ports + 2 Gigabit Ethernet PD ports

cevModuleCat2960cG8TC  OBJECT IDENTIFIER
    ::= { cevModuleCat29xxType 53 }

-- Catalyst 2960c 8 10/100/1000 ports + 2 dual purpose Gigabit Ethernet ports module

cevModuleCat292824TCC  OBJECT IDENTIFIER
    ::= { cevModuleCat29xxType 54 }

-- Catalyst 2928 24 10/100 + 2 10/100/1000 Ethernet ports module

cevModuleCat292824LTC  OBJECT IDENTIFIER
    ::= { cevModuleCat29xxType 55 }

-- Catalyst 24 10/100 ports with 8 POE ports + 2 10/100/1000 Ethernet ports. POE support for 123 W

cevModuleCat292848TCC  OBJECT IDENTIFIER
    ::= { cevModuleCat29xxType 56 }

-- Catalyst 2928 48 10/100 + 2 10/100/1000 Ethernet ports module

cevModuleWsC2960C8tcS  OBJECT IDENTIFIER
    ::= { cevModuleCat29xxType 57 }

-- Catalyst 2960C 8 10/100 FE ports + 2 Gig Dual Media Uplinks fixed configuration Layer 2 Ethernet switch, lanlite only

cevModuleWsC2960C8tcL  OBJECT IDENTIFIER
    ::= { cevModuleCat29xxType 58 }

-- Catalyst 2960C 8 10/100 FE ports + 2 Gig Dual Media Uplinks fixed configuration Layer 2 Ethernet switch

cevModuleWsC2960C8pcL  OBJECT IDENTIFIER
    ::= { cevModuleCat29xxType 59 }

-- Catalyst 2960C 8 10/100 FE with PoE + 2 Gig Dual Media Uplinks fixed configuration Layer 2 Ethernet switch

cevModuleWsC2960C12pcL  OBJECT IDENTIFIER
    ::= { cevModuleCat29xxType 60 }

-- Catalyst 2960C 12 10/100 FE with POE + 2 Gig Dual Media Uplinks fixed configuration Layer 2 Ethernet switch

cevModuleWsC2960x48fpdL  OBJECT IDENTIFIER
    ::= { cevModuleCat29xxType 68 }

-- Catalyst 2960X 48 Gig Downlinks, 2 SFP+ uplink, 2 x 10G stacking module, POE+ support for 740W

cevModuleWsC2960x48lpdL  OBJECT IDENTIFIER
    ::= { cevModuleCat29xxType 69 }

-- Catalyst 2960X 48 Gig Downlinks, 2 SFP+ uplink, 2 x 10G stacking module, POE+ support for 370W

cevModuleWsC2960x48tdL  OBJECT IDENTIFIER
    ::= { cevModuleCat29xxType 70 }

-- Catalyst 2960X 48 Gig Downlinks, 2 SFP+ uplink, 2 x 10G stacking module

cevModuleWsC2960x24pdL  OBJECT IDENTIFIER
    ::= { cevModuleCat29xxType 71 }

-- Catalyst 2960X 24 Gig Downlinks, 2 SFP+ uplink, 2 x 10G stacking module, POE+ support for 370W

cevModuleWsC2960x24tdL  OBJECT IDENTIFIER
    ::= { cevModuleCat29xxType 72 }

-- Catalyst 2960X 24 Gig Downlinks, 2 SFP+ uplink, 2 x 10G stacking module

cevModuleWsC2960x48fpsL  OBJECT IDENTIFIER
    ::= { cevModuleCat29xxType 73 }

-- Catalyst 2960X 48 Gig Downlinks, 4 SFP uplink with support for 2 x 10G stacking module, POE+ support for 740W

cevModuleWsC2960x48lpsL  OBJECT IDENTIFIER
    ::= { cevModuleCat29xxType 74 }

-- Catalyst 2960X 48 Gig Downlinks, 4 SFP uplink with support for 2 x 10G stacking module, POE+ support for 370W

cevModuleWsC2960x24psL  OBJECT IDENTIFIER
    ::= { cevModuleCat29xxType 75 }

-- Catalyst 2960X 24 Gig Downlinks, 4 SFP uplink with support for 2 x 10G stacking module, POE+ support for 370W

cevModuleWsC2960x48tsL  OBJECT IDENTIFIER
    ::= { cevModuleCat29xxType 76 }

-- Catalyst 2960X 48 Gig Downlinks, 4 SFP uplink with support for 2 x 10G stacking module

cevModuleWsC2960x24tsL  OBJECT IDENTIFIER
    ::= { cevModuleCat29xxType 77 }

-- Catalyst 2960X 24 Gig Downlinks, 4 SFP uplink with support for 2 x 10G stacking module

cevModuleWsC2960x24pskL  OBJECT IDENTIFIER
    ::= { cevModuleCat29xxType 78 }

-- Catalyst 2960X 24 Gig Downlinks, 4 SFP uplink NonStakable

cevModuleWsC2960x48lpsS  OBJECT IDENTIFIER
    ::= { cevModuleCat29xxType 79 }

-- Catalyst 2960X 48 Gig Downlinks, 2 SFP uplink Non Stackable, POE+ support for 370W

cevModuleWsC2960x24psS  OBJECT IDENTIFIER
    ::= { cevModuleCat29xxType 80 }

-- Catalyst 2960X 24 Gig Downlinks, 2 SFP uplink Non Stackable, POE+ support for 370W

cevModuleWsC2960x48tsLL  OBJECT IDENTIFIER
    ::= { cevModuleCat29xxType 81 }

-- Catalyst 2960X 48 Gig Downlinks, 2 SFP uplink Non Stackable

cevModuleWsC2960x24tsLL  OBJECT IDENTIFIER
    ::= { cevModuleCat29xxType 82 }

-- Catalyst 2960X 24 Gig Downlinks, 2 SFP uplink Non Stackable

cevModuleC2960XStack  OBJECT IDENTIFIER
    ::= { cevModuleCat29xxType 83 }

-- Arcadia Stacking module for 2960x

cevModuleC2960XFex  OBJECT IDENTIFIER
    ::= { cevModuleCat29xxType 84 }

-- Arcadia- FEX Stacking module for FEX

cevModuleC2960XFexStack  OBJECT IDENTIFIER
    ::= { cevModuleCat29xxType 85 }

-- Arcadia-FEX  + Stack, Stacking module for FEX

cevModuleWsC2960P48PstL  OBJECT IDENTIFIER
    ::= { cevModuleCat29xxType 86 }

-- 48-port PoE, 2+2 1G uplinks, LAN Base

cevModuleWsC2960P24PcL  OBJECT IDENTIFIER
    ::= { cevModuleCat29xxType 87 }

-- 24-port PoE, 2/2 1G uplinks, LAN Base

cevModuleWsC2960P24LcL  OBJECT IDENTIFIER
    ::= { cevModuleCat29xxType 88 }

-- 24-port, partial PoE 2/2 1G uplinks, LAN Base

cevModuleWsC2960P48TcL  OBJECT IDENTIFIER
    ::= { cevModuleCat29xxType 89 }

-- 48-port, 2/2 1G uplinks, LAN Base

cevModuleWsC2960P24TcL  OBJECT IDENTIFIER
    ::= { cevModuleCat29xxType 90 }

-- 24-port, 2/2 1G uplinks, LAN Base

cevModuleWsC2960P48PstS  OBJECT IDENTIFIER
    ::= { cevModuleCat29xxType 91 }

-- 48-port PoE, 2+2 1G uplinks, LAN Lite

cevModuleWsC2960P24PcS  OBJECT IDENTIFIER
    ::= { cevModuleCat29xxType 92 }

-- 24-port PoE, 2/2 1G uplinks, LAN Lite

cevModuleWsC2960P24LcS  OBJECT IDENTIFIER
    ::= { cevModuleCat29xxType 93 }

-- 24-port, partial PoE 2/2 1G uplinks, LAN Lite

cevModuleWsC2960P48TcS  OBJECT IDENTIFIER
    ::= { cevModuleCat29xxType 94 }

-- 48-port, 2/2 1G uplinks, LAN Lite

cevModuleWsC2960P24TcS  OBJECT IDENTIFIER
    ::= { cevModuleCat29xxType 95 }

-- 24-port, 2/2 1G uplinks, LAN Lite

cevModuleOscillatorType  OBJECT IDENTIFIER
    ::= { cevModule 24 }

-- Chip that sits on the CPU card, used for network timing.

cevStratum3  OBJECT IDENTIFIER
    ::= { cevModuleOscillatorType 1 }

-- Clock quality is Stratum 3

cevStratum4  OBJECT IDENTIFIER
    ::= { cevModuleOscillatorType 2 }

-- Clock quality is Stratum 4

cevModuleDslamType  OBJECT IDENTIFIER
    ::= { cevModule 25 }

-- Cards that go into the Cisco 6100, 6130, and 6260 DSLAM Chassis.  Does not include the Cisco 6200 Chassis.

cevNi2WanOc3mmSubOc3mm  OBJECT IDENTIFIER
    ::= { cevModuleDslamType 1 }

-- Network Interface module (OC-3-MM WAN, OC-3-MM Subtend)

cevNi2WanDs3Sub2Ds3  OBJECT IDENTIFIER
    ::= { cevModuleDslamType 2 }

-- Network Interface module (DS-3 WAN, 2 DS-3 Subtend)

cevAtuc1p2Cap  OBJECT IDENTIFIER
    ::= { cevModuleDslamType 3 }

-- ATU-C dual-line CAP module

cevAtuc1p2Dmt  OBJECT IDENTIFIER
    ::= { cevModuleDslamType 4 }

-- ATU-C dual-line DMT module

cevAtuc1p4Dmt  OBJECT IDENTIFIER
    ::= { cevModuleDslamType 5 }

-- ATU-C quad-line DMT module

cevLim  OBJECT IDENTIFIER
    ::= { cevModuleDslamType 6 }

-- Line Interface Module

cevNi2WanOc3smSubOc3sm  OBJECT IDENTIFIER
    ::= { cevModuleDslamType 7 }

-- Network Interface module (OC-3-SM WAN, OC-3-SM Subtend)

cevNi2WanE3Sub2E3  OBJECT IDENTIFIER
    ::= { cevModuleDslamType 8 }

-- Network Interface module (E-3 WAN, 2 E-3 Subtend)

cevNi2WanDs3Sub8Ds1Ima  OBJECT IDENTIFIER
    ::= { cevModuleDslamType 9 }

-- Network Interface module (DS-3 WAN, 8 DS-1 IMA Subtend)

cevAtuc1p4Cap  OBJECT IDENTIFIER
    ::= { cevModuleDslamType 10 }

-- ATU-C quad-line CAP module

cevStuc1p4  OBJECT IDENTIFIER
    ::= { cevModuleDslamType 11 }

-- STU-C quad-line module

cevAtuc1p4FlexiDmt  OBJECT IDENTIFIER
    ::= { cevModuleDslamType 13 }

-- Flexi DSL line card configured as DMT

cevAtuc1p4FlexiCap  OBJECT IDENTIFIER
    ::= { cevModuleDslamType 14 }

-- Flexi DSL line card configured as CAP

cevAtuc1p4Flexi  OBJECT IDENTIFIER
    ::= { cevModuleDslamType 15 }

-- Generic Flexi DSL line card

cevAtuc1p4DmtIsdn  OBJECT IDENTIFIER
    ::= { cevModuleDslamType 16 }

-- DMT over ISDN 4 port line card

cevNi2WanOc3smSub2Ds3  OBJECT IDENTIFIER
    ::= { cevModuleDslamType 17 }

-- Network Interface module (OC-3-SM WAN, 2 DS-3 Subtend)

cevNi2WanOc3mmSub2Ds3  OBJECT IDENTIFIER
    ::= { cevModuleDslamType 18 }

-- Network Interface module (OC-3-MM WAN, 2 DS-3 Subtend)

cevAtuc1p8DmtItemp  OBJECT IDENTIFIER
    ::= { cevModuleDslamType 21 }

-- ATU-C octal-line DMT module industrial temperature grade

cevStuc1p8Itemp  OBJECT IDENTIFIER
    ::= { cevModuleDslamType 22 }

-- STU-C octal-line shdsl module industrial temperature grade

cevNi2WanDs3Sub2Ds3Rev2  OBJECT IDENTIFIER
    ::= { cevModuleDslamType 35 }

-- Network Interface module (DS-3 WAN, DS-3 Subtend) Revision 2

cevNi2WanOc3smSubOc3smRev2  OBJECT IDENTIFIER
    ::= { cevModuleDslamType 36 }

-- Network Interface module (OC-3-SM WAN, OC-3-SM Subtend) Revision 2

cevNi2WanOc3mmSubOc3mmRev2  OBJECT IDENTIFIER
    ::= { cevModuleDslamType 37 }

-- Network Interface module (OC-3-MM WAN, OC-3-MM Subtend) Revision 2

cevNi2WanOc3smSub2Ds3Rev2  OBJECT IDENTIFIER
    ::= { cevModuleDslamType 38 }

-- Network Interface module (OC-3-SM WAN, 2 DS-3 Subtend) Revision 2

cevNi2WanOc3mmSub2Ds3Rev2  OBJECT IDENTIFIER
    ::= { cevModuleDslamType 39 }

-- Network Interface module (OC-3-MM WAN, 2 DS-3 Subtend) Revision 2

cevNi2WanOc3smSubOc3smItemp  OBJECT IDENTIFIER
    ::= { cevModuleDslamType 40 }

-- Network Interface module (OC-3-SM WAN, OC-3-SM Subtend, Itemp)

cevIo6100DS3  OBJECT IDENTIFIER
    ::= { cevModuleDslamType 43 }

-- 6100/6130 Network I/O module (3 DS3)

cevIo6160DS3  OBJECT IDENTIFIER
    ::= { cevModuleDslamType 44 }

-- 6160 Network I/O module (3 DS3)

cevIo6260OC3  OBJECT IDENTIFIER
    ::= { cevModuleDslamType 45 }

-- 6260 Network I/O module (2 OC3)

cevIo6260Ds3T1  OBJECT IDENTIFIER
    ::= { cevModuleDslamType 46 }

-- 6260 Network I/O module (DS3, 8 T1)
--   
-- These back cards defined under "cevModuleWASBackCards" are also called
-- Line Modules.  These Line Modules can be plugged into the connectors on
-- Service Modules defined under "cevWASCommonCards".  The same back card
-- can be used under multiple Service Module types.

cevModuleWASBackCards  OBJECT IDENTIFIER
    ::= { cevModule 26 }

cevLmBnc2t3  OBJECT IDENTIFIER
    ::= { cevModuleWASBackCards 1 }

-- Two T3 75-ohm BNC back card

cevLmBnc2e3  OBJECT IDENTIFIER
    ::= { cevModuleWASBackCards 2 }

-- Two E3 75-ohm BNC back card

cevLmDb154x21  OBJECT IDENTIFIER
    ::= { cevModuleWASBackCards 3 }

-- Four X.21 DB-15 back card

cevLmScsi22hssi  OBJECT IDENTIFIER
    ::= { cevModuleWASBackCards 4 }

-- Two HSSI SCSI-2 back card

cevLmRj488t1  OBJECT IDENTIFIER
    ::= { cevModuleWASBackCards 5 }

-- Eight T1 RJ48 back card

cevLmRj488t1R  OBJECT IDENTIFIER
    ::= { cevModuleWASBackCards 6 }

-- Eight T1 RJ48 redundancy back card

cevLmRj488e1  OBJECT IDENTIFIER
    ::= { cevModuleWASBackCards 7 }

-- Eight E1 RJ48 back card

cevLmRj488e1R  OBJECT IDENTIFIER
    ::= { cevModuleWASBackCards 8 }

-- Eight E1 RJ48 redundancy back card

cevLmSmb8e1  OBJECT IDENTIFIER
    ::= { cevModuleWASBackCards 9 }

-- Eight E1 SMB back card

cevLmSmb8e1R  OBJECT IDENTIFIER
    ::= { cevModuleWASBackCards 10 }

-- Eight E1 SMB redundancy back card

cevLmPsmUI  OBJECT IDENTIFIER
    ::= { cevModuleWASBackCards 11 }

-- User Interface back card containing 2 RS-232 ports and one ethernet port, T1/E1 timing reference ports for Processor Switch Modules

cevLmMmf4oc3  OBJECT IDENTIFIER
    ::= { cevModuleWASBackCards 12 }

-- 4 port 155Mbps back card, MMF, SC connectors

cevLmSmfIr4oc3  OBJECT IDENTIFIER
    ::= { cevModuleWASBackCards 13 }

-- 4 port 155Mbps back card, SMF-IR, SC connectors

cevLmSmfLr4oc3  OBJECT IDENTIFIER
    ::= { cevModuleWASBackCards 14 }

-- 4 port 155Mbps back card, SMF-LR, SC connectors

cevLmSmfIr1oc12  OBJECT IDENTIFIER
    ::= { cevModuleWASBackCards 15 }

-- 1 port 622Mbps back card, SMF-IR, FC connectors

cevLmSmfLr1oc12  OBJECT IDENTIFIER
    ::= { cevModuleWASBackCards 16 }

-- 1 port 622Mbps back card, SMF-LR, FC connectors

cevLmS3Ui  OBJECT IDENTIFIER
    ::= { cevModuleWASBackCards 17 }

-- Processor Switch Module (PXM) Stratum 3 User Interface back card for PXM1 or PXM2

cevLm1feTx  OBJECT IDENTIFIER
    ::= { cevModuleWASBackCards 18 }

-- 1 port Fast Ethernet RJ45 connector back card for MGX8800 RPM module

cevLm1feFx  OBJECT IDENTIFIER
    ::= { cevModuleWASBackCards 19 }

-- 1 port Fast Ethernet MMF connector back card for MGX8800 RPM module

cevLm1mmfFddi  OBJECT IDENTIFIER
    ::= { cevModuleWASBackCards 20 }

-- 1 port FDDI MMF connector back card for MGX8800 RPM module

cevLm1smfFddi  OBJECT IDENTIFIER
    ::= { cevModuleWASBackCards 21 }

-- 1 port FDDI SMF connector back card for MGX8800 RPM module

cevLmRj454e  OBJECT IDENTIFIER
    ::= { cevModuleWASBackCards 22 }

-- 4 port Ethernet (10BaseT) RJ45 connector back card for MGX8800 RPM module

cevLmMmf8oc3  OBJECT IDENTIFIER
    ::= { cevModuleWASBackCards 23 }

-- 8 port 155Mbps back card, MMF, Small Form Factor MT-RJ connectors

cevLmSmfIr8oc3  OBJECT IDENTIFIER
    ::= { cevModuleWASBackCards 24 }

-- 8 port 155Mbps back card, SMF-IR, Small Form Factor MT-RJ connectors

cevLmSmfLr8oc3  OBJECT IDENTIFIER
    ::= { cevModuleWASBackCards 25 }

-- 8 port 155Mbps back card, SMF-LR, Small Form Factor MT-RJ connectors

cevLmSmfIr1oc48  OBJECT IDENTIFIER
    ::= { cevModuleWASBackCards 26 }

-- 1 port 2488Mbps back card, SMF-IR, FC connector

cevLmSmfLr1oc48  OBJECT IDENTIFIER
    ::= { cevModuleWASBackCards 27 }

-- 1 port 2488Mbps back card, SMF-LR, FC connector

cevLmPsmHD  OBJECT IDENTIFIER
    ::= { cevModuleWASBackCards 28 }

-- Hard Disk back card for Processor Service Module

cevLmSmb8t3  OBJECT IDENTIFIER
    ::= { cevModuleWASBackCards 29 }

-- 8 port T3 back card, SMB connector

cevLmSmb8e3  OBJECT IDENTIFIER
    ::= { cevModuleWASBackCards 30 }

-- 8 port E3 back card, SMB connector

cevLmSmb4stm1  OBJECT IDENTIFIER
    ::= { cevModuleWASBackCards 31 }

-- 4 port 155-mbps Electrical Back Card, SMB Connector

cevLmSmfIr2oc12  OBJECT IDENTIFIER
    ::= { cevModuleWASBackCards 32 }

-- 2 Port 622-Mbps Back card SMF-IR

cevLmSmfLr2oc12  OBJECT IDENTIFIER
    ::= { cevModuleWASBackCards 33 }

-- 2 Port 622-Mbps Back card SMF-LR

cevLmSmfSr1oc48  OBJECT IDENTIFIER
    ::= { cevModuleWASBackCards 34 }

-- 1 Port 2488-Mbps, Short Reach(SR), SMF-SR back card

cevLmSmfXlr1oc48  OBJECT IDENTIFIER
    ::= { cevModuleWASBackCards 35 }

-- 1 Port 2488-Mbps, Extended Long Reach(XLR), SMF-XLR back card

cevLmBnc3t3  OBJECT IDENTIFIER
    ::= { cevModuleWASBackCards 36 }

-- 3 T3 Back Card , BNC Connector

cevLmSmfIr1Oc48B  OBJECT IDENTIFIER
    ::= { cevModuleWASBackCards 37 }

-- 1 Port 2488-Mbps, SMF-IR(Intermediate Reach) Back card Version B, SC Connector

cevLmSmfLr1Oc48B  OBJECT IDENTIFIER
    ::= { cevModuleWASBackCards 38 }

-- 1 Port 2488-Mbps, SMF-LR (Long reach )Back card Version B, SC Connector

cevLmSmfSr1Oc48B  OBJECT IDENTIFIER
    ::= { cevModuleWASBackCards 39 }

-- 1 Port 2488-Mbps, SMF-SR (Short Reach) Back card Version B, SC Connector

cevLmSmfIr2Oc12B  OBJECT IDENTIFIER
    ::= { cevModuleWASBackCards 40 }

-- 2 Port 622-Mbps, SMF-IR(Intermediate reach) Back card Version B, SC Connector

cevLmSmfLr2Oc12B  OBJECT IDENTIFIER
    ::= { cevModuleWASBackCards 41 }

-- 2 Port 622-Mbps, SMF-LR(Long reach) Back card Version B, SC Connector

cevLmSmfIr1Oc12C  OBJECT IDENTIFIER
    ::= { cevModuleWASBackCards 42 }

-- 1 Port 622-Mbps, SMFIR-2-622/C(Intermediate Reach) Back card, SC Connector

cevLmSmfLr1Oc12C  OBJECT IDENTIFIER
    ::= { cevModuleWASBackCards 43 }

-- 1 Port 622-Mbps, SMFLR-2-622/C (Long reach )Back card, SC Connector

cevLmMmf4Oc3C  OBJECT IDENTIFIER
    ::= { cevModuleWASBackCards 44 }

-- 4 Port 155-Mbps, MMF-4-155/C (Multi Mode Fiber) Back card, SC Connector

cevLmSmfIr4Oc3C  OBJECT IDENTIFIER
    ::= { cevModuleWASBackCards 45 }

-- 4 Port 155-Mbps, SMFIR-4-155/C (Intermediate Reach) Back card, SC Connector

cevLmSmfLr4Oc3C  OBJECT IDENTIFIER
    ::= { cevModuleWASBackCards 46 }

-- 4 Port 155-Mbps, SMFLR-4-155/C (Long reach) Back card, SC Connector

cevLmSmfXlr1Oc48B  OBJECT IDENTIFIER
    ::= { cevModuleWASBackCards 51 }

-- 1 port 2488-Mbps,  Extended Long Reach(XLR) SMF-XLR  back card for ATM Switch Service Module B

cevLm1feTxcp  OBJECT IDENTIFIER
    ::= { cevModuleWASBackCards 55 }

-- 1 port Fast Ethernet RJ-45 connector back card with co-processor assist for the MGX8800 RPM PR module

cevLmSmfIr8Oc3C  OBJECT IDENTIFIER
    ::= { cevModuleWASBackCards 58 }

-- 8 port, 155Mbps, SMFIR-8-155LC/C (Intermediate Reach) Back Card, LC Connector

cevLmSmfLr8Oc3C  OBJECT IDENTIFIER
    ::= { cevModuleWASBackCards 59 }

-- 8 port, 155Mbps, SMFLR-8-155LC/C (Long Reach) Back Card, LC Connector

cevLmMmf8Oc3C  OBJECT IDENTIFIER
    ::= { cevModuleWASBackCards 60 }

-- 8 port, 155Mbps, MMF-8-155C Back Card, LC Connector

cevLmSmfIr1Oc3  OBJECT IDENTIFIER
    ::= { cevModuleWASBackCards 61 }

-- 1 port, 155Mbps, SMFIR-1-155 (Intermediate Reach) Back Card

cevLmSmfLr1Oc3  OBJECT IDENTIFIER
    ::= { cevModuleWASBackCards 62 }

-- 1 port, 155Mbps, SMFLR-1-155 (Long Reach) Back Card

cevLmSmb1Stm1  OBJECT IDENTIFIER
    ::= { cevModuleWASBackCards 63 }

-- MGX SMB 1 port STM1 Back Card

cevLmScsi2B2hssi  OBJECT IDENTIFIER
    ::= { cevModuleWASBackCards 64 }

-- Two HSSI SCSI-2/B Back Card

cevLm12In18s  OBJECT IDENTIFIER
    ::= { cevModuleWASBackCards 65 }

-- 12In1-8s Back Card

cevLmSmb6e3  OBJECT IDENTIFIER
    ::= { cevModuleWASBackCards 66 }

-- 6 E3 ports SMB Back Card

cevLmComboT3E3Oc3  OBJECT IDENTIFIER
    ::= { cevModuleWASBackCards 67 }

-- PXM1E-COMBO-T3E3-155'S Back Card supporting 8 T3/E3 ports and 4 OC3 ports

cevLmRj488t1e1  OBJECT IDENTIFIER
    ::= { cevModuleWASBackCards 68 }

-- Eight T1/E1 RJ-48 Back Card

cevLmMcc16e1  OBJECT IDENTIFIER
    ::= { cevModuleWASBackCards 69 }

-- 16 E1 Port Miniature Coaxial Connector (MCC) Back Card

cevLmRj4816t1e1  OBJECT IDENTIFIER
    ::= { cevModuleWASBackCards 70 }

-- Sixteen T1/E1 RJ-48 Back Card

cevLmSmfIr2Oc12c  OBJECT IDENTIFIER
    ::= { cevModuleWASBackCards 71 }

-- 2 port, 622Mbps, SMFIR-2-622LC/C (Intermediate Reach) Back Card, LC Connector

cevLmSmfLr2Oc12c  OBJECT IDENTIFIER
    ::= { cevModuleWASBackCards 72 }

-- 2 port, 622Mbps, SMFLR-2-622LC/C (Long Reach) Back Card, LC Connector

cevLmSmb8Stm1  OBJECT IDENTIFIER
    ::= { cevModuleWASBackCards 82 }

-- 8 port 155-mbps Electrical Back Card, SMB Connector

cevLmSmf8Oc3Sfp  OBJECT IDENTIFIER
    ::= { cevModuleWASBackCards 83 }

-- SMF-8-155-SFP SMF(Single Mode Fiber) 8 OC3 Small Form Factor Pluggable(SFP) backcard

cevLmRbbn16t1e1  OBJECT IDENTIFIER
    ::= { cevModuleWASBackCards 84 }

-- RBBN-16-T1E1 A "Ribbon" type connector supporting 16 T1 or E1 ports.

cevLmSmfSr1Oc192  OBJECT IDENTIFIER
    ::= { cevModuleWASBackCards 85 }

-- Line Module with 1 OC192 SMF SR(short reach) port

cevLmSmfIr1Oc192  OBJECT IDENTIFIER
    ::= { cevModuleWASBackCards 86 }

-- Line Module with 1 OC192 SMF IR(Intermediate reach) port

cevLmSmfLr1Oc192  OBJECT IDENTIFIER
    ::= { cevModuleWASBackCards 87 }

-- Line Module with 1 OC192 SMF LR(Long reach) port

cevLmSmfXlr1Oc192  OBJECT IDENTIFIER
    ::= { cevModuleWASBackCards 88 }

-- Line Module with 1 OC192 SMF XLR(Extended long reach) port

cevLmMcc8oc3  OBJECT IDENTIFIER
    ::= { cevModuleWASBackCards 89 }

-- 8 OC3 Port Miniature Coaxial Connector (MCC) Back Card

cevLmRbbn16t1e11N  OBJECT IDENTIFIER
    ::= { cevModuleWASBackCards 92 }

-- RBBN-16-T1E1-1N, A "Ribbon" type connector for 16 T1 or E1 interfaces with support for 1:N

cevLmMcc16e11N  OBJECT IDENTIFIER
    ::= { cevModuleWASBackCards 93 }

-- MCC-16-E1-1N, A Miniature Coaxial Connector for 16 E1 interfaces with support for 1:N

cevLmRed16t1e1  OBJECT IDENTIFIER
    ::= { cevModuleWASBackCards 94 }

-- RED-16-T1E1, 1:N Redundant Backcard for 16 T1 or E1 interfaces

cevLmSfp2Oc3  OBJECT IDENTIFIER
    ::= { cevModuleWASBackCards 95 }

-- MPSM 2 port small form pluggable OC3 or STS half height Backcard

cevLmSmb2Oc3EL  OBJECT IDENTIFIER
    ::= { cevModuleWASBackCards 96 }

-- MPSM 2 port electrical OC3 or STS half height Backcard

cevLmBnc3t3e3  OBJECT IDENTIFIER
    ::= { cevModuleWASBackCards 97 }

-- MPSM 3 port T3 or E3 half height Backcard

cevLmRed2Oc3  OBJECT IDENTIFIER
    ::= { cevModuleWASBackCards 98 }

-- MPSM redundant half height Backcard which supports 2 redundant OC3 or STS ports

cevLmRed3t3e3  OBJECT IDENTIFIER
    ::= { cevModuleWASBackCards 99 }

-- MPSM redundant half height Backcard which supports 3 redundant T3 or E3 ports

cevLmSmf4Oc12  OBJECT IDENTIFIER
    ::= { cevModuleWASBackCards 100 }

-- Four OC12 port single mode (SMF) Back Card

cevLmChamp24t1e1  OBJECT IDENTIFIER
    ::= { cevModuleWASBackCards 101 }

-- VXSM back card with card type:VXSM-BC-CHAMP-24T1E1

cevLmSmb3t3e3  OBJECT IDENTIFIER
    ::= { cevModuleWASBackCards 102 }

-- VXSM back card with card type:VXSM-BC-SMB-3T3E3

cevLmVxsmSmfIr4Oc3  OBJECT IDENTIFIER
    ::= { cevModuleWASBackCards 103 }

-- VXSM back card with card type: VXSM-SMFIR-4-155 for  Cisco MGX cevChassisMGX8850 chassis

cevLmVxsmSmfLr4Oc3  OBJECT IDENTIFIER
    ::= { cevModuleWASBackCards 104 }

-- VXSM back card with card type: VXSM-SMFLR-4-155 for  Cisco MGX cevChassisMGX8850 chassis

cevLmVxsm4Oc3R  OBJECT IDENTIFIER
    ::= { cevModuleWASBackCards 105 }

-- VXSM Service Redundancy Module supporting 4 OC3 ports, used to provide 1:N redundancy

cevLmVxsmMmf4Oc3  OBJECT IDENTIFIER
    ::= { cevModuleWASBackCards 106 }

-- VXSM back card with card type: VXSM_BC_MMF_4_155 for  Cisco MGX cevChassisMGX8850 chassis

cevLm4V35  OBJECT IDENTIFIER
    ::= { cevModuleWASBackCards 107 }

-- 4 V.35 type back card

cevLm4X21  OBJECT IDENTIFIER
    ::= { cevModuleWASBackCards 108 }

-- 4 X.21 type back card

cevLmMgxXfUIB  OBJECT IDENTIFIER
    ::= { cevModuleWASBackCards 109 }

-- Management back card Model B for RPM-XF with 2 RJ-45 RS232 ports and 2 Fast Ethernet Ports

cevLm5efegeTx  OBJECT IDENTIFIER
    ::= { cevModuleWASBackCards 110 }

-- 5 port Ethernet/Fast Ethernet/Gigabit Ethernet auto sense backcard for MGX RPM-PR module.

cevLmPsmHDV  OBJECT IDENTIFIER
    ::= { cevModuleWASBackCards 111 }

-- Hard Disk V back card for Processor Service Module

cevModuleUbrType  OBJECT IDENTIFIER
    ::= { cevModule 27 }

-- Cards that go into UBR chassis

cevUbrMc16s  OBJECT IDENTIFIER
    ::= { cevModuleUbrType 2 }

-- Cable card, 1 downstream 6 upstream for Spectrum Management

cevUbrMc11  OBJECT IDENTIFIER
    ::= { cevModuleUbrType 3 }

-- Cable linecard 1 downstream, 1 upstream, FPGA

cevUbrMc11c  OBJECT IDENTIFIER
    ::= { cevModuleUbrType 4 }

-- Cable linecard 1 downstream, 1 upstream, ASIC C

cevUbrMc12c  OBJECT IDENTIFIER
    ::= { cevModuleUbrType 5 }

-- Cable linecard 1 downstream, 2 upstream, ASIC C

cevUbrMc14c  OBJECT IDENTIFIER
    ::= { cevModuleUbrType 6 }

-- Cable linecard 1 downstream, 4 upstream, ASIC C

cevUbrMc16a  OBJECT IDENTIFIER
    ::= { cevModuleUbrType 7 }

-- Cable linecard 1 downstream, 6 upstream, ASIC A

cevUbrMc16b  OBJECT IDENTIFIER
    ::= { cevModuleUbrType 8 }

-- Cable linecard 1 downstream, 6 upstream, ASIC B

cevUbrMc16c  OBJECT IDENTIFIER
    ::= { cevModuleUbrType 9 }

-- Cable linecard 1 downstream, 6 upstream, ASIC C

cevUbrMc16e  OBJECT IDENTIFIER
    ::= { cevModuleUbrType 10 }

-- Cable linecard 1 downstream, 6 upstream, ASIC for Europe

cevUbrMc28c  OBJECT IDENTIFIER
    ::= { cevModuleUbrType 11 }

-- Cable linecard 2 downstream, 8 upstream

cevUbrMc26  OBJECT IDENTIFIER
    ::= { cevModuleUbrType 12 }

-- Cable linecard 2 downstream, 6 upstream

cevUbr912C  OBJECT IDENTIFIER
    ::= { cevModuleUbrType 13 }

-- Cisco uBR912-C Cable Modem Card with CSU/DSU WIC

cevUbr912S  OBJECT IDENTIFIER
    ::= { cevModuleUbrType 14 }

-- Cisco uBR912-S Cable Modem Card with Serial WIC

cevUbr914R  OBJECT IDENTIFIER
    ::= { cevModuleUbrType 15 }

-- Cisco uBR914 Cable Modem Card with removable WIC

cevUbrClk  OBJECT IDENTIFIER
    ::= { cevModuleUbrType 16 }

-- Cisco Cable Clock Card that provides the national clock signal to Cisco uBR7200 VXR

cevUbr925  OBJECT IDENTIFIER
    ::= { cevModuleUbrType 17 }

-- Cisco UBR925 Cable Modem/Router with VOIP and hardware accelerated IPSEC

cevUbrMc26c  OBJECT IDENTIFIER
    ::= { cevModuleUbrType 18 }

-- Cable linecard 2 downstream, 6 upstream

cevUbrMc28cf  OBJECT IDENTIFIER
    ::= { cevModuleUbrType 21 }

-- Cable linecard 2 downstream, 8 upstream, with F connector

cevUbrMc28cBnc  OBJECT IDENTIFIER
    ::= { cevModuleUbrType 22 }

-- Cable linecard 2 downstream, 8 upstream, with BNC connector

cevUbrMc26cf  OBJECT IDENTIFIER
    ::= { cevModuleUbrType 23 }

-- Cable linecard 2 downstream, 6 upstream, with F connector

cevUbrMc26cBnc  OBJECT IDENTIFIER
    ::= { cevModuleUbrType 24 }

-- Cable linecard 2 downstream, 6 upstream, with BNC connector

cevUbrDlc24  OBJECT IDENTIFIER
    ::= { cevModuleUbrType 26 }

-- DLC24 is a Digital Video Broadcasting (DVB) Linecard which supports the DVB in-band (IB) and out-of-band (OOB) standards, as well as the DAVIC OOB standard.  It has 2 downstream channels, 4 upstream channels, and 1 ASI interface port

cevUbrMc28j  OBJECT IDENTIFIER
    ::= { cevModuleUbrType 33 }

-- Cable modem linecard, 2 downstream, 8 upstream at 5-55MHz

cevUbrMc28u  OBJECT IDENTIFIER
    ::= { cevModuleUbrType 34 }

-- Docsis compliant intelligent coax cable line card with 2 downstream and 8 upstream ports for ubr72xx series cable routers.

cevUbrMc16u  OBJECT IDENTIFIER
    ::= { cevModuleUbrType 35 }

-- Docsis compliant intelligent coax cable line card with 1 downstream and 6 upstream ports for ubr72xx series cable routers.

cevUbrMc28x  OBJECT IDENTIFIER
    ::= { cevModuleUbrType 36 }

-- Docsis compliant intelligent coax cable line card with 2 upstream and 8 downstream ports and integrated upstream for ubr72xx routers.

cevUbrMc16x  OBJECT IDENTIFIER
    ::= { cevModuleUbrType 37 }

-- Docsis compliant intelligent coax cable line card with 1 upstream and 6 downstream ports and integrated upstream converter for ubr72xx routers.

cevUbrMc520uD  OBJECT IDENTIFIER
    ::= { cevModuleUbrType 38 }

-- uBR10K Universal Card, 5DS w/upx, 20US, Spec An

cevUbrMc520uF  OBJECT IDENTIFIER
    ::= { cevModuleUbrType 39 }

-- uBR10K Universal Card, 5DS w/upx, 20US, Spec An,F

cevUbrTccPlus  OBJECT IDENTIFIER
    ::= { cevModuleUbrType 41 }

-- uBR10K Timing, Communications and Control Plus Card

cevUbrMc16uE  OBJECT IDENTIFIER
    ::= { cevModuleUbrType 42 }

-- DOCSIS compliant intelligent coax cable line card with 1 downstream and 6  upstream ports for uBR7225VXR series cable routers

cevUbrMc28uE  OBJECT IDENTIFIER
    ::= { cevModuleUbrType 43 }

-- DOCSIS compliant intelligent coax cable line card with 2 downstream and 8  upstream ports for uBR7225VXR series cable routers

cevUbrDtcc  OBJECT IDENTIFIER
    ::= { cevModuleUbrType 44 }

-- DOCSIS Timing, Communication, and Control Plus Card for uBR10012

cevUbrMc88v  OBJECT IDENTIFIER
    ::= { cevModuleUbrType 46 }

-- DOCSIS 3.0 compliant intelligent coax cable line card with 8 downstream and 8  upstream ports

cevUbrmc2020  OBJECT IDENTIFIER
    ::= { cevModuleUbrType 47 }

-- DOCSIS compliant intelligent coax cable line card with 20 downstream and 20 upstream ports for uBR10000 series cable router

cevModuleCmccType  OBJECT IDENTIFIER
    ::= { cevModule 28 }

-- Cisco Mainframe Channel Connection Cards

cevCmccCip  OBJECT IDENTIFIER
    ::= { cevModuleCmccType 1 }

-- Channel Interface Processor for the C75xx platform

cevCmccCip2  OBJECT IDENTIFIER
    ::= { cevModuleCmccType 2 }

-- Channel Interface Processor 2 for the C75xx platform

cevCmccPa1ec  OBJECT IDENTIFIER
    ::= { cevModuleCmccType 3 }

-- Escon Channel Port Adapter (Supports single ESCON interface)

cevCmccPa1pc  OBJECT IDENTIFIER
    ::= { cevModuleCmccType 4 }

-- Parallel (Bus & Tag) Channel Port Adapter (Supports single parallel interface)

cevCmccPa1ec4  OBJECT IDENTIFIER
    ::= { cevModuleCmccType 5 }

-- High Performance ESCON Channel Port Adapter Version 4

cevModuleCat6000Type  OBJECT IDENTIFIER
    ::= { cevModule 29 }

-- Catalyst 6000 Cards

cevCat6kWsxSup12ge  OBJECT IDENTIFIER
    ::= { cevModuleCat6000Type 2 }

-- Supervisor with 2 Gigabit Ethernet ports

cevCat6kWsx6408Gbic  OBJECT IDENTIFIER
    ::= { cevModuleCat6000Type 3 }

-- Card with 8 Gigabit Ethernet ports

cevCat6kWsx6224Fx100Mt  OBJECT IDENTIFIER
    ::= { cevModuleCat6000Type 4 }

-- Card with 24 port 100BaseFX MM (MT-RJ) for the Catalyst 6000 series

cevCat6kWsx6248Rj45  OBJECT IDENTIFIER
    ::= { cevModuleCat6000Type 5 }

-- Card with 48 10/100 RJ45 Fast Ethernet ports

cevCat6kWsx6248Tel  OBJECT IDENTIFIER
    ::= { cevModuleCat6000Type 6 }

-- Card with 48 10/100 RJ21 Fast Ethernet ports

cevCat6kWsx6302Msm  OBJECT IDENTIFIER
    ::= { cevModuleCat6000Type 7 }

-- Multilayer Switch Module for the Catalyst 6000 series

cevCat6kWsx6024Mtrj  OBJECT IDENTIFIER
    ::= { cevModuleCat6000Type 9 }

-- Card with 24 10/100 MTRJ Fast Ethernet ports

cevCat6kMsfc2  OBJECT IDENTIFIER
    ::= { cevModuleCat6000Type 10 }

-- Multilevel Switching Feature Card Version 2 for Catalyst 6000 that is treated as a standalone system by the NMS

cevCat6kWsx6316GeTx  OBJECT IDENTIFIER
    ::= { cevModuleCat6000Type 11 }

-- 16-port RJ-45 Gigabit ethernet module

cevCat6kWsx6416Gbic  OBJECT IDENTIFIER
    ::= { cevModuleCat6000Type 12 }

-- 16-port GBIC Gigabit ethernet module

cevCat6kWsx6324100Fx  OBJECT IDENTIFIER
    ::= { cevModuleCat6000Type 13 }

-- 24-port 100FX multimode MT-RJ with 128K per-port packet buffer

cevCat6kWsx6348Rj45  OBJECT IDENTIFIER
    ::= { cevModuleCat6000Type 14 }

-- 48-port 10/100 ethernet module

cevCat6kWsx650210ge  OBJECT IDENTIFIER
    ::= { cevModuleCat6000Type 15 }

-- 10 Gigabit Ethernet Base Module

cevCat6kWsx6066SlbApc  OBJECT IDENTIFIER
    ::= { cevModuleCat6000Type 16 }

-- Venus: Server Load Balancing Application Processor Complex

cevCat6kWsx6548Rj45  OBJECT IDENTIFIER
    ::= { cevModuleCat6000Type 18 }

-- 48 port 10/100 Hydra2+/Hydra2V+

cevCat6kWsx6248aTel  OBJECT IDENTIFIER
    ::= { cevModuleCat6000Type 19 }

-- Card for C6K with 48 10/100 RJ21 ports with enhanched QoS a.k.a Indus w/ Enhanced QoS

cevCat6kWsxSup22ge  OBJECT IDENTIFIER
    ::= { cevModuleCat6000Type 20 }

-- Supervisor 2 with 2 Gigabit Ethernet ports

cevCat6kWsc6500SFM  OBJECT IDENTIFIER
    ::= { cevModuleCat6000Type 21 }

-- Catalyst 6500 Switch Fabric Module

cevCat6kWsc6500SFM2  OBJECT IDENTIFIER
    ::= { cevModuleCat6000Type 22 }

-- Catalyst 6500 Switch Fabric Module II

cevCat6kWsx6816GBIC  OBJECT IDENTIFIER
    ::= { cevModuleCat6000Type 23 }

-- Catalyst 6500 16 port 1000BaseX (Layer 3)

cevCat6kWsx6600Audio  OBJECT IDENTIFIER
    ::= { cevModuleCat6000Type 27 }

-- Catalyst 6000 256-Audio Services Module

cevCat6kWsx6348RJ21  OBJECT IDENTIFIER
    ::= { cevModuleCat6000Type 28 }

-- Catalyst 6500 48 port 10/100BaseTX (RJ-21)

cevCat6kWsx6516GBIC  OBJECT IDENTIFIER
    ::= { cevModuleCat6000Type 29 }

-- Catalyst 6500 16 port 1000BaseX (GBIC)

cevCat6kWsxSup1a2ge  OBJECT IDENTIFIER
    ::= { cevModuleCat6000Type 30 }

-- Catalyst 6500 2 port 1000BaseX Supervisor module (GBIC)

cevCat6kWsx6548RJ21  OBJECT IDENTIFIER
    ::= { cevModuleCat6000Type 31 }

-- Catalyst 6500 48 port 10/100BaseTX (RJ-21)

cevCat6kWsx6416GEMT  OBJECT IDENTIFIER
    ::= { cevModuleCat6000Type 32 }

-- Catalyst 6500 16 port 1000BaseSX (MT-RJ)

cevCat6kWsx6380NAM  OBJECT IDENTIFIER
    ::= { cevModuleCat6000Type 33 }

-- Catalyst 6500 Network Analysis Module

cevCat6kWsx6248aRJ45  OBJECT IDENTIFIER
    ::= { cevModuleCat6000Type 34 }

-- Catalyst 6500 48 port 10/100BaseTX (RJ-45)

cevCat6kWsx6408aGbic  OBJECT IDENTIFIER
    ::= { cevModuleCat6000Type 35 }

-- Catalyst 6500 8 port 1000BaseX (GBIC), Enhanced QoS module

cevCat6kWsx6381IDS  OBJECT IDENTIFIER
    ::= { cevModuleCat6000Type 36 }

-- Catalyst 6500 Intrusion Detection module

cevCat6kWsx6524MmMT  OBJECT IDENTIFIER
    ::= { cevModuleCat6000Type 37 }

-- Catalyst 6500 24 port 100BaseX MM (MT-RJ) module

cevCat6kWsx6516GeTx  OBJECT IDENTIFIER
    ::= { cevModuleCat6000Type 38 }

-- Catalyst 6500 16 port 10/100/1000BaseT (RJ-45) module

cevCat6kWsx650110Gex4  OBJECT IDENTIFIER
    ::= { cevModuleCat6000Type 39 }

-- Catalyst 6500 1 port 10 Gigabit Ethernet (EX4) module

cevCat6kWsx6816Oc3Mm  OBJECT IDENTIFIER
    ::= { cevModuleCat6000Type 40 }

-- Catalyst 6500 16 port OC3c Packet Over Sonet Multimode

cevCat6kWsf6kVpwr  OBJECT IDENTIFIER
    ::= { cevModuleCat6000Type 41 }

-- Catalyst 6500 inline power card

cevCat6kWsSvcNam1  OBJECT IDENTIFIER
    ::= { cevModuleCat6000Type 42 }

-- Catalyst 6500 Network AnalysisModule

cevCat6kWsSvcNam2  OBJECT IDENTIFIER
    ::= { cevModuleCat6000Type 43 }

-- Catalyst 6500 Network AnalysisModule

cevCat6kWsSvcFwm1  OBJECT IDENTIFIER
    ::= { cevModuleCat6000Type 44 }

-- Catalyst 6500 Firewall Module

cevCat6kWsSvcSsl1  OBJECT IDENTIFIER
    ::= { cevModuleCat6000Type 45 }

-- Catalyst 6500 SSL Module

cevCat6kWsx6516aGBIC  OBJECT IDENTIFIER
    ::= { cevModuleCat6000Type 46 }

-- Catalyst 6500 16 port1000BaseX (GBIC)

cevCat6kIpSecVPNSm  OBJECT IDENTIFIER
    ::= { cevModuleCat6000Type 49 }

-- Gigabit IPsec VPN Service Module for the Catalyst 6500 and 7600

cevCat6kWsSup720  OBJECT IDENTIFIER
    ::= { cevModuleCat6000Type 50 }

-- Catalyst 6500 Supervisor Module 720 CPU board

cevCat6kWsSup720Base  OBJECT IDENTIFIER
    ::= { cevModuleCat6000Type 51 }

-- Catalyst 6500 Supervisor Module 720 base board

cevCat6kWsx680210Ge  OBJECT IDENTIFIER
    ::= { cevModuleCat6000Type 52 }

-- Catalyst 6500 2 port 10 GE

cevCat6kWsx6832Sfp  OBJECT IDENTIFIER
    ::= { cevModuleCat6000Type 53 }

-- Catalyst 6500 32 port 1000Base FX (SFP GBIC)

cevCat6kWsx6748GeTx  OBJECT IDENTIFIER
    ::= { cevModuleCat6000Type 54 }

-- Catalyst 6500 48 port 10/100/1000 (RJ-45)

cevCat6kWsx670410Ge  OBJECT IDENTIFIER
    ::= { cevModuleCat6000Type 55 }

-- Catalyst 6500 4 port 10 GE

cevCat6kWsx6748Sfp  OBJECT IDENTIFIER
    ::= { cevModuleCat6000Type 56 }

-- Catalyst 6500 48 port 1000Base FX (SFP GBIC)

cevCat6kWsx6724Sfp  OBJECT IDENTIFIER
    ::= { cevModuleCat6000Type 57 }

-- Catalyst 6500 24 port 1000Base FX (SFP GBIC)

cevCat6kWsf6kPfc  OBJECT IDENTIFIER
    ::= { cevModuleCat6000Type 58 }

-- Catalyst 6500 L3 switching engine

cevCat6kWsf6kPfc2  OBJECT IDENTIFIER
    ::= { cevModuleCat6000Type 59 }

-- Catalyst 6500 L3 switching engine II

cevCat6kWsf6kDfc  OBJECT IDENTIFIER
    ::= { cevModuleCat6000Type 60 }

-- Catalyst 6500 distributed switching engine

cevCat6kWsf6kPfc3a  OBJECT IDENTIFIER
    ::= { cevModuleCat6000Type 61 }

-- Catalyst 6500 Centralized L3 switching engine IIIa

cevCat6kWsf6kDfc3a  OBJECT IDENTIFIER
    ::= { cevModuleCat6000Type 62 }

-- Catalyst 6500 Distributed L3 switching engine IIIa

cevCat6kWsx6148GeTx  OBJECT IDENTIFIER
    ::= { cevModuleCat6000Type 63 }

-- Catalyst 6000 48 port10/100/1000BaseT(RJ-45) module

cevCat6kWsx6148Rj21  OBJECT IDENTIFIER
    ::= { cevModuleCat6000Type 64 }

-- Catalyst 6000 48 port10/100BaseTX(RJ-21) module

cevCat6kWsx6148Rj45  OBJECT IDENTIFIER
    ::= { cevModuleCat6000Type 65 }

-- Catalyst 6000 48 port10/100BaseTX(RJ-45) module

cevCat6kMWAMBlade  OBJECT IDENTIFIER
    ::= { cevModuleCat6000Type 66 }

-- Mobile wireless application module for the Catalyst 6500 and Cisco 7600.

cevCat6kWsx6548GeTx  OBJECT IDENTIFIER
    ::= { cevModuleCat6000Type 67 }

-- Catalyst 6500 48 port 10/100/1000 (RJ-45)

cevCat6kWsf6700dfc3a  OBJECT IDENTIFIER
    ::= { cevModuleCat6000Type 68 }

-- Catalyst 6500 Distributed L3 switching engine IIIa

cevCat6kWsx6324100FxSm  OBJECT IDENTIFIER
    ::= { cevModuleCat6000Type 69 }

-- 24-port 100FX single mode MT-RJ with 128K per-port packet buffer

cevCat6kWsc6000cl  OBJECT IDENTIFIER
    ::= { cevModuleCat6000Type 70 }

-- Catalyst 6000 clock module

cevCat6kWsc6513cl  OBJECT IDENTIFIER
    ::= { cevModuleCat6000Type 71 }

-- Catalyst 6000 clock module for WS-C6513

cevClk7600  OBJECT IDENTIFIER
    ::= { cevModuleCat6000Type 72 }

-- Clock module for Cisco 7600

cevCat6kWsc6kvtt  OBJECT IDENTIFIER
    ::= { cevModuleCat6000Type 73 }

-- Catalyst 6000 VTT module

cevCat6kWsx6302aMsm  OBJECT IDENTIFIER
    ::= { cevModuleCat6000Type 74 }

-- Multilayer Switch Module (Rev. A) for the Catalyst 6000 series

cevCat6kMemC6kAta164M  OBJECT IDENTIFIER
    ::= { cevModuleCat6000Type 75 }

-- 64MB ATA-1 flash card for Catalyst 6000

cevCat6kMemC6kCptfl64M  OBJECT IDENTIFIER
    ::= { cevModuleCat6000Type 76 }

-- 64MB compact flash card for Catalyst 6000

cevCat6kMemC6kCptfl128M  OBJECT IDENTIFIER
    ::= { cevModuleCat6000Type 77 }

-- 128MB compact flash card for Catalyst 6000

cevCat6kMemC6kCptfl256M  OBJECT IDENTIFIER
    ::= { cevModuleCat6000Type 78 }

-- 256MB compact flash card for Catalyst 6000

cevCat6kMemC6kFlc16M  OBJECT IDENTIFIER
    ::= { cevModuleCat6000Type 79 }

-- 16MB PCMCIA flash card for Catalyst 6000

cevCat6kMemC6kFlc24M  OBJECT IDENTIFIER
    ::= { cevModuleCat6000Type 80 }

-- 24MB PCMCIA flash card for Catalyst 6000

cevCat6kWsSvcIdsm2  OBJECT IDENTIFIER
    ::= { cevModuleCat6000Type 81 }

-- Catalyst 6500 Intrusion Detection Module

cevCat6kWssvcidsupg  OBJECT IDENTIFIER
    ::= { cevModuleCat6000Type 82 }

-- Catalyst 6500 IDS 2 accelerator board

cevCat6kWsx6148x2Rj45  OBJECT IDENTIFIER
    ::= { cevModuleCat6000Type 83 }

-- Catalyst 6500 96-port 10/100BaseTX (RJ-45) module

cevCat6kWsf6kFe48x2Af  OBJECT IDENTIFIER
    ::= { cevModuleCat6000Type 84 }

-- Catalyst 6500 Inline voice daughter card

cevCat6kWsf6kFe48Af  OBJECT IDENTIFIER
    ::= { cevModuleCat6000Type 85 }

-- Cat6k voice daughter cards

cevCat6kWsf6kGe48Af  OBJECT IDENTIFIER
    ::= { cevModuleCat6000Type 86 }

-- Cat6k voice daughter cards

cevCat6kWsf6kVpwrGe  OBJECT IDENTIFIER
    ::= { cevModuleCat6000Type 87 }

-- Cat6k voice daughter cards

cevCat6kWsf6700cfc  OBJECT IDENTIFIER
    ::= { cevModuleCat6000Type 88 }

-- Catalyst 6500 centralized Forwarding Card

cevCat6kWsSvcWlan1K9  OBJECT IDENTIFIER
    ::= { cevModuleCat6000Type 89 }

-- Catalyst 6500 Wireless LAN module

cevCat6kWsx6624Fxs  OBJECT IDENTIFIER
    ::= { cevModuleCat6000Type 90 }

-- Catalyst 6000 24 port FXS Analog Station Interface Module

cevCat6kWsSvcAon1  OBJECT IDENTIFIER
    ::= { cevModuleCat6000Type 91 }

-- Application-Oriented Networking (AON) Service Module

cevCat6kWsSup32ge  OBJECT IDENTIFIER
    ::= { cevModuleCat6000Type 92 }

-- Catalyst 6500 Supervisor Module with 8 Gigabit Ethernet SFP uplink ports

cevCat6kWsSup3210ge  OBJECT IDENTIFIER
    ::= { cevModuleCat6000Type 93 }

-- Catalyst 6500 Supervisor Module with 2 10-GE uplinnk ports

cevCat6kPSDBlade  OBJECT IDENTIFIER
    ::= { cevModuleCat6000Type 94 }

-- Provides persistent storage facilities

cevCat6kWsc6kvtte  OBJECT IDENTIFIER
    ::= { cevModuleCat6000Type 95 }

-- Catalyst 6000 VTT-E module

cevCat6kWsx6066SlbsK9  OBJECT IDENTIFIER
    ::= { cevModuleCat6000Type 98 }

-- CSM-S is a content switching module with integrated SSL acceleration

cevCat6kWsf6kpfc3b  OBJECT IDENTIFIER
    ::= { cevModuleCat6000Type 99 }

-- Catalyst 6500 Policy feature card 3B

cevCat6kWsf6kdfc3b  OBJECT IDENTIFIER
    ::= { cevModuleCat6000Type 100 }

-- Catalyst 6500 Distributed forwarding card 3B

cevCat6kWsf6700dfc3b  OBJECT IDENTIFIER
    ::= { cevModuleCat6000Type 101 }

-- Catalyst 6500 Distributed forwarding card 3B

cevCat6kWsf6kpfc3bxl  OBJECT IDENTIFIER
    ::= { cevModuleCat6000Type 102 }

-- Catalyst 6500 Policy feature card 3B XL

cevCat6kWsf6kdfc3bxl  OBJECT IDENTIFIER
    ::= { cevModuleCat6000Type 103 }

-- Catalyst 6500 Distributed forwarding card 3B XL

cevCat6kWsf6700dfc3bxl  OBJECT IDENTIFIER
    ::= { cevModuleCat6000Type 104 }

-- Catalyst 6500 Distributed forwarding card 3B XL

cevCat6kCsg  OBJECT IDENTIFIER
    ::= { cevModuleCat6000Type 105 }

-- Content Services Gateway

cevCat6kMsfc2a  OBJECT IDENTIFIER
    ::= { cevModuleCat6000Type 106 }

-- Multilevel Switching Feature Card Version 2a for Catalyst 6000 that is treated as a standalone system by the NMS

cevCat6kWs6340Sup  OBJECT IDENTIFIER
    ::= { cevModuleCat6000Type 107 }

-- ME6340 Supervisor

cevCat6kWs6340LcA  OBJECT IDENTIFIER
    ::= { cevModuleCat6000Type 108 }

-- ME6340 48 port ADSL 2/2+ Annex A Module

cevCat6kWs6340LcB  OBJECT IDENTIFIER
    ::= { cevModuleCat6000Type 109 }

-- ME6340 48 port ADSL 2/2+ Annex B Module

cevCat6kMec6524gs8s  OBJECT IDENTIFIER
    ::= { cevModuleCat6000Type 110 }

-- Catalyst 6524 module with 24 port SFP and 8 SFP uplinks

cevCat6kMec6524gt8s  OBJECT IDENTIFIER
    ::= { cevModuleCat6000Type 111 }

-- Catalyst 6524 module with 24 port 10/100/1000BaseT and 8 SFP uplinks

cevCat6kMec6524Msfc2a  OBJECT IDENTIFIER
    ::= { cevModuleCat6000Type 114 }

-- Catalyst 6524 and 6724 Multilevel Switching Feature Card Version 2a

cevCat6kMec6524Pfc3c  OBJECT IDENTIFIER
    ::= { cevModuleCat6000Type 115 }

-- Catalyst 6524 and 6724 L3 switching engine

cevCat6kWsx6196Rj21  OBJECT IDENTIFIER
    ::= { cevModuleCat6000Type 116 }

-- Catalyst 6500 96 port 10/100BaseTX (RJ-21) module

cevCat6kWsx6148FeSfp  OBJECT IDENTIFIER
    ::= { cevModuleCat6000Type 117 }

-- Catalyst 6500 48 port 100Base-X SFP module

cevCat6kWsx6148aGeTx  OBJECT IDENTIFIER
    ::= { cevModuleCat6000Type 118 }

-- Catalyst 6500 48 port 10/100/1000BaseTX (RJ-45) module

cevCat6kWsx6148aRj45  OBJECT IDENTIFIER
    ::= { cevModuleCat6000Type 119 }

-- Catalyst 6500 48 port 10/100BaseTX (RJ-45) module

cevCat6kAce10K9  OBJECT IDENTIFIER
    ::= { cevModuleCat6000Type 120 }

-- Application Control Engine(ACE) Service Module

cevCat6kWsg6483  OBJECT IDENTIFIER
    ::= { cevModuleCat6000Type 122 }

-- Catalyst 6500 10GE-ER Serial 1550nm extended reach module

cevCat6kWsg6485  OBJECT IDENTIFIER
    ::= { cevModuleCat6000Type 123 }

-- Catalyst 6500 10GE-LX4 Campus 1310nm WWDM long haul/short reach module

cevCat6kWsg6488  OBJECT IDENTIFIER
    ::= { cevModuleCat6000Type 124 }

-- Catalyst 6500 10GE-LR Serial 1310nm long haul module

cevCat6kWsg6489  OBJECT IDENTIFIER
    ::= { cevModuleCat6000Type 125 }

-- Catalyst 6500 10GE-SX4 850nm WWDM short reach module

cevCat6kWsSvcWebVpnK9  OBJECT IDENTIFIER
    ::= { cevModuleCat6000Type 126 }

-- Catalyst 6500 Web VPN Module

cevCat6kSAMIBB  OBJECT IDENTIFIER
    ::= { cevModuleCat6000Type 127 }

-- Service and Application Module for IP

cevCat6kWsx6708a10ge  OBJECT IDENTIFIER
    ::= { cevModuleCat6000Type 128 }

-- Catalyst 6500 8 port 10 GE

cevCat6kWsx670810ge  OBJECT IDENTIFIER
    ::= { cevModuleCat6000Type 129 }

-- Catalyst 6500 8 port 10 GE with DFC

cevCat6kWsf6700Dfc3c  OBJECT IDENTIFIER
    ::= { cevModuleCat6000Type 131 }

-- Catalyst 6500 Distributed forwarding card 3C

cevCat6kWsf6700Dfc3cxl  OBJECT IDENTIFIER
    ::= { cevModuleCat6000Type 132 }

-- Catalyst 6500 Distributed forwarding card 3C XL

cevCat6kVsS72010G  OBJECT IDENTIFIER
    ::= { cevModuleCat6000Type 133 }

-- Catalyst 6500 Supervisor 720 with 10G Ethernet Module

cevCat6kVsf6kPfc3c  OBJECT IDENTIFIER
    ::= { cevModuleCat6000Type 134 }

-- Catalyst 6500 Policy Feature Card 3C

cevCat6kVsf6kPfc3cxl  OBJECT IDENTIFIER
    ::= { cevModuleCat6000Type 135 }

-- Catalyst 6500 Policy Feature Card 3C XL

cevCat6kVsF6kMsfc3  OBJECT IDENTIFIER
    ::= { cevModuleCat6000Type 136 }

-- Supervisor Module 720 10G CPU board

cevCat6kWsF6kPisa  OBJECT IDENTIFIER
    ::= { cevModuleCat6000Type 137 }

-- Catalyst 6500 Programmable IP Services Accelerator Internal Router Daughtercard

cevCat6kVsF6kPfc4xl  OBJECT IDENTIFIER
    ::= { cevModuleCat6000Type 138 }

-- Catalyst 6500 Policy Feature Card 4 XL

cevCat6kWsF6kDfc4exl  OBJECT IDENTIFIER
    ::= { cevModuleCat6000Type 139 }

-- Catalyst 6500 Distributed Forwarding Card 4E XL

cevCat6kWsx671610Ge  OBJECT IDENTIFIER
    ::= { cevModuleCat6000Type 142 }

-- Catalyst 6500 16 port 10 GE

cevCat6kVsF6kPfc4  OBJECT IDENTIFIER
    ::= { cevModuleCat6000Type 143 }

-- Catalyst 6500 Policy Feature Card 4

cevCat6kWsF6kDfc4e  OBJECT IDENTIFIER
    ::= { cevModuleCat6000Type 144 }

-- Catalyst 6500 Distributed Forwarding Card 4E

cevCat6kWsSup32Pge  OBJECT IDENTIFIER
    ::= { cevModuleCat6000Type 145 }

-- Catalyst 6500 Supervisor Module with PISA and 8 Gigabit Ethernet SFP uplink ports

cevCat6kWsSup32P10ge  OBJECT IDENTIFIER
    ::= { cevModuleCat6000Type 146 }

-- Catalyst 6500 Supervisor Module with PISA and 2 10-GE uplinnk ports

cevCat6kWsx690810g  OBJECT IDENTIFIER
    ::= { cevModuleCat6000Type 148 }

-- Catalyst 6500 8 port 10 GE with TrustSec

cevCat6kWsc6513Ecl  OBJECT IDENTIFIER
    ::= { cevModuleCat6000Type 155 }

-- Catalyst 6000 clock module for WS-C6513E chassis

cevCat6kWsSvcWism  OBJECT IDENTIFIER
    ::= { cevModuleCat6000Type 156 }

-- Wireless Service Module for the Catalyst 6500 and 7600

cevCat6kWsSvcNam1S250  OBJECT IDENTIFIER
    ::= { cevModuleCat6000Type 157 }

-- Catalyst 6500 Network Analysis Module (NAM)

cevCat6kWsSvcNam2S250  OBJECT IDENTIFIER
    ::= { cevModuleCat6000Type 158 }

-- Catalyst 6500 Network Analysis Module (NAM)

cevCat6kWsF6kDfc4a  OBJECT IDENTIFIER
    ::= { cevModuleCat6000Type 159 }

-- Catalyst 6500 Distributed Forwarding Card 4A

cevCat6kWsF6kDfc4axl  OBJECT IDENTIFIER
    ::= { cevModuleCat6000Type 160 }

-- Catalyst 6500 Distributed Forwarding Card 4A XL

cevCat6kVsSup2t10g  OBJECT IDENTIFIER
    ::= { cevModuleCat6000Type 163 }

-- Catalyst 6500 Supervisor Module VS-SUP2T-10G

cevCat6kVsF6kMsfc5  OBJECT IDENTIFIER
    ::= { cevModuleCat6000Type 164 }

-- Catalyst 6500 MPC8572 Dual-core CPU Daughter Board

cevCat6kWsf6k48At  OBJECT IDENTIFIER
    ::= { cevModuleCat6000Type 166 }

-- Catalyst 6500 IEEE 802.3at inline power voice daughter card

cevCat6kWsx6148eGe45At  OBJECT IDENTIFIER
    ::= { cevModuleCat6000Type 167 }

-- Catalyst 6500 48-port IEEE802.3at compliant Power over Ethernet Plus module with inline power voice daughter card

cevCat6kWsx671610T  OBJECT IDENTIFIER
    ::= { cevModuleCat6000Type 168 }

-- Catalyst 6500 16 port 10 GE RJ-45

cevCat6kWsSvcAsaSm1  OBJECT IDENTIFIER
    ::= { cevModuleCat6000Type 169 }

-- Adaptive Security Appliance (ASA) Service Module for Catalyst switches msgreene

cevCat6kWsx6148eGeTx  OBJECT IDENTIFIER
    ::= { cevModuleCat6000Type 172 }

-- Catalyst 6500 48-port IEEE802.3at compliant Power over Ethernet Plus module

cevCat6kWsx690440g  OBJECT IDENTIFIER
    ::= { cevModuleCat6000Type 174 }

-- Catalyst 6500 4-port 40GE and 16-port 10GE

cevCat6kWsSvcNam3K9  OBJECT IDENTIFIER
    ::= { cevModuleCat6000Type 175 }

-- Next generation Network Analysis Module msgreene

cevCat6kWsx6848Tx  OBJECT IDENTIFIER
    ::= { cevModuleCat6000Type 176 }

-- Catalyst 6500 48-port 10/100/1000 (RJ-45)

cevCat6kWsx6848sfp  OBJECT IDENTIFIER
    ::= { cevModuleCat6000Type 178 }

-- Catalyst 6500 48-port 1000Base FX(SFP)

cevCat6kWsx6824sfp  OBJECT IDENTIFIER
    ::= { cevModuleCat6000Type 179 }

-- Catalyst 6500 24-port 1000Base FX(SFP)

cevCat6kWsx681610ge  OBJECT IDENTIFIER
    ::= { cevModuleCat6000Type 181 }

-- Catalyst 6500 16-port 10 GE (X2)

cevCat6kWsx681610t  OBJECT IDENTIFIER
    ::= { cevModuleCat6000Type 182 }

-- Catalyst 6500 16-port 10 GE (RJ-45)

cevCat6kACE20K9  OBJECT IDENTIFIER
    ::= { cevModuleCat6000Type 184 }

-- Application Control Engine Module (Product ID:ACE04-6500-K9)

cevCat6kWsSvcWism2  OBJECT IDENTIFIER
    ::= { cevModuleCat6000Type 185 }

-- Wireless Service Module-2 for the Catalyst 6500

cevCat6kWsSvcAsaSm1K7  OBJECT IDENTIFIER
    ::= { cevModuleCat6000Type 186 }

-- Adaptive Security Appliance (ASA) with No Payload Encryption (NPE)

cevModuleCat5000Type  OBJECT IDENTIFIER
    ::= { cevModule 30 }

-- Catalyst 5000 Cards

cevCat5kRsfc  OBJECT IDENTIFIER
    ::= { cevModuleCat5000Type 1 }

-- Routing Switching Feature Card

cevModule7100Type  OBJECT IDENTIFIER
    ::= { cevModule 31 }

-- Cards that go into the 7100 series (7120 and 7140)

cevIo2feTxIsl  OBJECT IDENTIFIER
    ::= { cevModule7100Type 1 }

-- I/O Card Dual 10/100 Fast Ethernet ISL

cevIsmIpsecMppe  OBJECT IDENTIFIER
    ::= { cevModule7100Type 2 }

-- Integrated Service Module, used only in slot 5 of the 7100 series, is a hardware accelerator for IPSEC Encryption and Compression, and MPPE encryption.

cev7100VPNAccelerator  OBJECT IDENTIFIER
    ::= { cevModule7100Type 3 }

-- VPN Encryption Accelerator Engine

cev7100VPNAcceleratorModule2  OBJECT IDENTIFIER
    ::= { cevModule7100Type 4 }

-- VPN Encryption Accelerator Engine 2

cev7100VPNAcceleratorAES  OBJECT IDENTIFIER
    ::= { cevModule7100Type 5 }

-- VPN Encryption Accelerator Engine with AES Support

cev7100VPNAM2Plus  OBJECT IDENTIFIER
    ::= { cevModule7100Type 6 }

-- The VPN Acceleration Module 2+ (VAM2+) is a port adapter that installs in any single port-adapter slot on the Cisco 7204VXR or Cisco 7206VXR router with the NPE-225, NPE-400, or NPE-G1 processor, or the Cisco 7301 router.

cevModule10000Type  OBJECT IDENTIFIER
    ::= { cevModule 32 }

-- Cards that go into the 10x00 series router platform

cevPos1oc12  OBJECT IDENTIFIER
    ::= { cevModule10000Type 1 }

-- 1 port OC12 Packet over Sonet card

cevP6Ct3  OBJECT IDENTIFIER
    ::= { cevModule10000Type 2 }

-- 6 port channelized T3 card

cevGe  OBJECT IDENTIFIER
    ::= { cevModule10000Type 3 }

-- 1 port Gigabit Ethernet card

cevAtm1Oc12  OBJECT IDENTIFIER
    ::= { cevModule10000Type 4 }

-- 1 Port OC12 ATM card

cevP1COc12  OBJECT IDENTIFIER
    ::= { cevModule10000Type 5 }

-- 1 Port channelized OC12 card

cevP4Chstm1  OBJECT IDENTIFIER
    ::= { cevModule10000Type 6 }

-- 4 port channelized STM-1 card

cev24feTx  OBJECT IDENTIFIER
    ::= { cevModule10000Type 8 }

-- c10720 24 ports fast ethernet Tx access card

cev24feFxMm  OBJECT IDENTIFIER
    ::= { cevModule10000Type 9 }

-- c10720 24 ports fast ethernet FX MM (2km) access card

cev24feFxSm  OBJECT IDENTIFIER
    ::= { cevModule10000Type 10 }

-- c10720 24 ports fast ethernet FX SM (15km) access card

cevSrpOc48SmSr  OBJECT IDENTIFIER
    ::= { cevModule10000Type 11 }

-- c10720 1 port OC-48c SRP SM short reach uplink card

cevSrpOc48SmIr  OBJECT IDENTIFIER
    ::= { cevModule10000Type 12 }

-- c10720 1 port OC-48c SRP SM intermediate reach uplink card

cevPos6oc3  OBJECT IDENTIFIER
    ::= { cevModule10000Type 13 }

-- 6 port OC3 Pocket over Sonet Card for the 10000 ESR

cevAtm4oc3  OBJECT IDENTIFIER
    ::= { cevModule10000Type 14 }

-- 4 port OC3 ATM line card with single mode, intermediate reach optics for the C10000 platform

cevP8E3Ds3  OBJECT IDENTIFIER
    ::= { cevModule10000Type 15 }

-- 8 port unchannalized switchable t3/e3

cevSrpPos1oc48SmSr  OBJECT IDENTIFIER
    ::= { cevModule10000Type 16 }

-- 1 Port OC48 SRP or POS SM short reach card

cevSrpPos1oc48SmLr  OBJECT IDENTIFIER
    ::= { cevModule10000Type 17 }

-- 1 Port OC48 SRP or POS SM long reach card

cevC10K48MbFlashCard  OBJECT IDENTIFIER
    ::= { cevModule10000Type 18 }

-- Cisco 10000 48 MB Flash Card

cevC10K128MbFlashCard  OBJECT IDENTIFIER
    ::= { cevModule10000Type 19 }

-- Cisco 10000 128 MB Flash Card

cevP24ChE1T1  OBJECT IDENTIFIER
    ::= { cevModule10000Type 22 }

-- 24 Port Channelized E1/T1 card

cev4Ge8FeTx  OBJECT IDENTIFIER
    ::= { cevModule10000Type 23 }

-- c10720 4 port gigabit ethernet + 8 port fast ethernet access card

cev4Ge8FeFxMm  OBJECT IDENTIFIER
    ::= { cevModule10000Type 24 }

-- c10720 4 port gigabit ethernet + 8 port fast ethernet FX MM (2km) access card

cev4Ge8FeFxSm  OBJECT IDENTIFIER
    ::= { cevModule10000Type 25 }

-- c10720 4 port gigabit ethernet + 8 port fast ethernet FX SM (15km) access card

cevSrpOc48SmLr1  OBJECT IDENTIFIER
    ::= { cevModule10000Type 26 }

-- 1 port OC-48c SRP SM Long Reach (40Km) uplink card

cevSrpOc48SmLr2  OBJECT IDENTIFIER
    ::= { cevModule10000Type 27 }

-- 1 port OC-48c SRP SM long reach (80Km) uplink card

cevP8Fe  OBJECT IDENTIFIER
    ::= { cevModule10000Type 30 }

-- 8 Port Fast Ethernet line card

cevP8Ds3E3Atm  OBJECT IDENTIFIER
    ::= { cevModule10000Type 31 }

-- 8 Port DS3/E3 ATM Line Card

cevC10720Mnt  OBJECT IDENTIFIER
    ::= { cevModule10000Type 32 }

-- C10720 Maintenance card

cevPosSrpOc48SmSr  OBJECT IDENTIFIER
    ::= { cevModule10000Type 34 }

-- c10720 OC-48c POS/SRP SM short reach uplink card

cevPosSrpOc48SmIr  OBJECT IDENTIFIER
    ::= { cevModule10000Type 35 }

-- c10720 OC-48c POS/SRP SM intermediate reach uplink card

cevPosSrpOc48SmLr1  OBJECT IDENTIFIER
    ::= { cevModule10000Type 36 }

-- c10720 OC-48c POS/SRP SM Long Reach (40Km) uplink card

cevPosSrpOc48SmLr2  OBJECT IDENTIFIER
    ::= { cevModule10000Type 37 }

-- c10720 OC-48c POS/SRP SM Long Reach (80Km) uplink card

cevC10KJacket  OBJECT IDENTIFIER
    ::= { cevModule10000Type 38 }

-- the Shared Port Adaptor (SPA) jacket (or host) card for the c10k.  It can host up to 2 SPAs

cev24feTxB  OBJECT IDENTIFIER
    ::= { cevModule10000Type 39 }

-- c10720 24 ports fast ethernet Tx access card revB.

cev4Ge8FeTxB  OBJECT IDENTIFIER
    ::= { cevModule10000Type 40 }

-- c10720 4 port gigabit ethernet + 8 port fast ethernet access card revB.

cevRprSrpOc48  OBJECT IDENTIFIER
    ::= { cevModule10000Type 41 }

-- c10720 1 port RPR(802.17)/SRP OC48 uplink card

cevP4Ct3  OBJECT IDENTIFIER
    ::= { cevModule10000Type 42 }

-- c10000 4 port channelized half-height T3 card

cevAtm4oc3stm1Lr  OBJECT IDENTIFIER
    ::= { cevModule10000Type 43 }

-- c10000 4 port OC3/STM1 ATM line card with long reach optics

cevModuleAs5400Type  OBJECT IDENTIFIER
    ::= { cevModule 33 }

-- Cards that go into the AS5400 series router platform

cevAs5400DfcCarrier  OBJECT IDENTIFIER
    ::= { cevModuleAs5400Type 1 }

-- Carrier card that holds Dial Feature Cards for the AS5400 platform

cevAs5400DfcNp348  OBJECT IDENTIFIER
    ::= { cevModuleAs5400Type 2 }

-- Nextport (np) Modem Dial Feature Card consisting of 3 modem modules, 2 of which have 120 modems and that has 108, for a total of 348 modems per card, used in AS5400 and AS5350 platforms

cevAs5400DfcNp192  OBJECT IDENTIFIER
    ::= { cevModuleAs5400Type 3 }

-- Nextport (np) Modem Dial Feature Card consisting of 2 modem modules, 1 of which has 120 modems the other 72, for a total of 192 modems per card, used in AS5400 and AS5350 platforms

cevAs5400XMDfcCarrier  OBJECT IDENTIFIER
    ::= { cevModuleAs5400Type 4 }

-- Carrier card that holds Dial Feature Cards for the AS5400-XM platform

cevAs5400XMVFC  OBJECT IDENTIFIER
    ::= { cevModuleAs5400Type 5 }

-- Voice Feature Card   containing Texas Instruments Digital Signal processor(DSP)

cevModuleCat4000Type  OBJECT IDENTIFIER
    ::= { cevModule 35 }

-- Catalyst 4000 Cards

cevCat4232L3  OBJECT IDENTIFIER
    ::= { cevModuleCat4000Type 1 }

-- Cisco Catalyst 4232-L3 layer 3 line card that is treated as a standalone system by the NMS

cevCat4kGateway  OBJECT IDENTIFIER
    ::= { cevModuleCat4000Type 2 }

-- Catalyst 4000 Access Gateway line card supporting voice and WAN (Wide Area Network) interfaces as well as conferencing and transcoding services for operation with the Cisco Call Manager

cevCat4kWsx4014  OBJECT IDENTIFIER
    ::= { cevModuleCat4000Type 3 }

-- Supervisor III Card

cevCat4kWsx4124FxMt  OBJECT IDENTIFIER
    ::= { cevModuleCat4000Type 4 }

-- Card with 24 100 FX ports and MTRJ connectors

cevCat4kWsx4148FxMt  OBJECT IDENTIFIER
    ::= { cevModuleCat4000Type 5 }

-- Card with 48 100 FX ports and MTRJ connectors

cevCat4kWsx4148Rj  OBJECT IDENTIFIER
    ::= { cevModuleCat4000Type 6 }

-- Card with 48 10/100 baseT ports

cevCat4kWsx4148Rj21  OBJECT IDENTIFIER
    ::= { cevModuleCat4000Type 7 }

-- Card with 48 10/100 baseT Telco ports

cevCat4kWsx4148Rj45V  OBJECT IDENTIFIER
    ::= { cevModuleCat4000Type 8 }

-- Card with 48 10/100 baseT voice power ports

cevCat4kWsx4232GbRj  OBJECT IDENTIFIER
    ::= { cevModuleCat4000Type 9 }

-- Card with 32 10/100 baseT and 2 1000 GBIC ports

cevCat4kWsx4232RjXx  OBJECT IDENTIFIER
    ::= { cevModuleCat4000Type 10 }

-- Card with 32 10/100 baseT and 2 1000 duaghtercard ports

cevCat4kWsx4306Gb  OBJECT IDENTIFIER
    ::= { cevModuleCat4000Type 11 }

-- Card with 6 1000 GBIC ports

cevCat4kWsx4418Gb  OBJECT IDENTIFIER
    ::= { cevModuleCat4000Type 12 }

-- Card with 18 1000 GBIC ports

cevCat4kWsx44122GbTx  OBJECT IDENTIFIER
    ::= { cevModuleCat4000Type 13 }

-- Card with 12 1000 TX and 2 1000 GBIC ports

cevCat4kWsx4424GbRj45  OBJECT IDENTIFIER
    ::= { cevModuleCat4000Type 14 }

-- Card with 48 10/100/1000 TX

cevCat4kWsx4448GbLx  OBJECT IDENTIFIER
    ::= { cevModuleCat4000Type 15 }

-- Card with 48 1000 LX

cevCat4kWsx4448GbRj45  OBJECT IDENTIFIER
    ::= { cevModuleCat4000Type 16 }

-- Card with 48 10/100/1000 TX

cevCat4kPEM  OBJECT IDENTIFIER
    ::= { cevModuleCat4000Type 17 }

-- Power Entry Module for Catalyst 4000

cevCat4kWsx4515  OBJECT IDENTIFIER
    ::= { cevModuleCat4000Type 18 }

-- Supervisor IV Card for Catalyst 4000

cevCat4kWsx4148LxMt  OBJECT IDENTIFIER
    ::= { cevModuleCat4000Type 19 }

-- Card with 48 100 LX ports and MTRJ connectors for Catalyst 4000

cevCat4kWsx4248Rj45V  OBJECT IDENTIFIER
    ::= { cevModuleCat4000Type 20 }

-- Card with 48 10/100 baseT voice power ports

cevCat4kWsx4516  OBJECT IDENTIFIER
    ::= { cevModuleCat4000Type 21 }

-- Supervisor V Card for Catalyst 4000

cevCat4kWsx4013Plus  OBJECT IDENTIFIER
    ::= { cevModuleCat4000Type 22 }

-- Supervisor II-Plus Card for Catalyst 4000

cevCat4kWsx4248Rj21V  OBJECT IDENTIFIER
    ::= { cevModuleCat4000Type 23 }

-- Card with 48 10/100 baseT Telco voice power ports

cevCat4kWsx4302Gb  OBJECT IDENTIFIER
    ::= { cevModuleCat4000Type 24 }

-- Card with 2 1000 GBIC ports

cevCat4kWsx4548GbRj45V  OBJECT IDENTIFIER
    ::= { cevModuleCat4000Type 25 }

-- Card with 48 10/100/1000 baseT voice power ports

cevCat4kWsx4548GbRj45  OBJECT IDENTIFIER
    ::= { cevModuleCat4000Type 26 }

-- 48-port 10/100/1000 line card for Catalyst4000

cevCat4kWsx4712Qam24B  OBJECT IDENTIFIER
    ::= { cevModuleCat4000Type 27 }

-- Card with 12 ports, each having 2 QAM (Quadrature Amplitude Modulation)channels, based on ITU-T J.83 Annex B.

cevCat4kWsx4148FeBdLc  OBJECT IDENTIFIER
    ::= { cevModuleCat4000Type 28 }

-- Card with 48 100 BX10-D ports and LC connectors for Catalyst 4000

cevCat4kWsx4124Rj  OBJECT IDENTIFIER
    ::= { cevModuleCat4000Type 29 }

-- Card with 24 10/100 baseT ports

cevCat4kWsx4224Rj45V  OBJECT IDENTIFIER
    ::= { cevModuleCat4000Type 30 }

-- Card with 24 10/100 baseT voice power ports

cevCat4kWsx4524GbRj45V  OBJECT IDENTIFIER
    ::= { cevModuleCat4000Type 31 }

-- Card with 24 10/100/1000 baseT voice power ports

cevCat4kWsx4506GBT  OBJECT IDENTIFIER
    ::= { cevModuleCat4000Type 32 }

-- 6 port nonblocking Gigabit RJ45 line card for Catalyst 4500 with options to use SFP instead of RJ45. RJ45 interface supports inline power

cevCat4kWsxSvcNam  OBJECT IDENTIFIER
    ::= { cevModuleCat4000Type 33 }

-- Catalyst 4000 Network Analysis Service Module

cevCat4kWsx4448GbSfp  OBJECT IDENTIFIER
    ::= { cevModuleCat4000Type 34 }

-- 48-port Gigabit SFP line card for Catalyst 4500, supporting SX, LX , and BX SFP's

cevCat4kWsX4013PlusTS  OBJECT IDENTIFIER
    ::= { cevModuleCat4000Type 35 }

-- Catalyst 4000 supervisor with 12 10/100/1000BaseT ports and 8 1000BaseX SFP ports

cevCat4kWsx4kClock  OBJECT IDENTIFIER
    ::= { cevModuleCat4000Type 36 }

-- Cat4K High Availability Clock Module containing two redundant clocks. This module is field replacable. The system has to be powered down to replace this module

cevCat4kWsx4948  OBJECT IDENTIFIER
    ::= { cevModuleCat4000Type 37 }

-- Catalyst 4000 series fixed configuration switch with 48 10/100/1000BaseT wirespeed ports and 4 1000BaseX SFP ports

cevCat4kWsx451610GE  OBJECT IDENTIFIER
    ::= { cevModuleCat4000Type 38 }

-- Supervisor V Card for Catalyst 4000 with 4 Gigabit SFPs and 2 Ten Gigabit X2s

cevCat4kWsx4013Plus10GE  OBJECT IDENTIFIER
    ::= { cevModuleCat4000Type 40 }

-- Supervisor II-PLUS-10GE card for Catalyst 4500 with 4 Gigabit SFPs and 2 Ten Gigabit X2s.

cevCat4kWsx494810GE  OBJECT IDENTIFIER
    ::= { cevModuleCat4000Type 42 }

-- Catalyst 4000 series fixed configuration switch with 48 10/100/1000BaseT wirespeed ports and 2 10Gbps X2 ports.

cevCat4kWsx4kMux  OBJECT IDENTIFIER
    ::= { cevModuleCat4000Type 43 }

-- Mux Buffers for Redundancy Logic.

cevCat4kWsx490410ge  OBJECT IDENTIFIER
    ::= { cevModuleCat4000Type 44 }

-- Catalyst 4900M series, half height line card with 4 port wire speed 10GE interface (WS-X4904-10GE)

cevCat4kWsx4900M  OBJECT IDENTIFIER
    ::= { cevModuleCat4000Type 45 }

-- Catalyst 4900M series chassis with fixed 8 10Gig port base system with 2 additional half height line card slots(WS-C4900M )

cevCat4kWsx490810ge  OBJECT IDENTIFIER
    ::= { cevModuleCat4000Type 46 }

-- Catalyst 4900M series, half height line card with 8 port 2:1 10GE interface (WS-X4908-10GE)

cevCat4kWsx4920Gbrj45  OBJECT IDENTIFIER
    ::= { cevModuleCat4000Type 47 }

-- Catalyst 4900M series, half height line card with 20 port 10/100/1000 RJ45 interface (WS-X4920-GB-RJ45)

cevCat4kWsx4590  OBJECT IDENTIFIER
    ::= { cevModuleCat4000Type 48 }

-- Catalyst 4507R/4510R Fabric Redundancy Module

cevCatWsx4624SfpE  OBJECT IDENTIFIER
    ::= { cevModuleCat4000Type 49 }

-- WS-X4624-SFP-E:1000BaseX (SFP) with 24 SFP ports. Linecard with 24 SFP ports providing 1-Gigabit non-blocking traffic on each port, for Catalyst-4500E series modular switches.

cevCat4kWsx492810GE  OBJECT IDENTIFIER
    ::= { cevModuleCat4000Type 50 }

-- Catalyst 4000 series fixed configuration switch with  28 One Gigabit SFP ports and 2 Ten Gigabit X2 ports

cevCat4kWsx4548GbRj45VPlus  OBJECT IDENTIFIER
    ::= { cevModuleCat4000Type 51 }

-- Card with 48 10/100/1000 baseT voice power ports and that is what we are using in our codebase.

cevCat4kWsx490810GRj45  OBJECT IDENTIFIER
    ::= { cevModuleCat4000Type 52 }

-- Catalyst 4900M series, half height line card with 8 port 2:1 10GE/1G RJ45 interface (WS-X4908-10GE-RJ45)

cevCat4kWsx4948ef10GE  OBJECT IDENTIFIER
    ::= { cevModuleCat4000Type 54 }

-- Catalyst 4900 series front exhaust fixed configuration switch with 48 10/100/1000BaseT ports and four 10Gbps/1Gbps SFP+/SFP ports(WS-C4948E-F)

cevCat4kC4kxNm8  OBJECT IDENTIFIER
    ::= { cevModuleCat4000Type 55 }

-- Cisco Catalyst 4500X series uplink module with 8 10GE SFP+ ports

cevCat4kWsx4500x16  OBJECT IDENTIFIER
    ::= { cevModuleCat4000Type 56 }

-- Cisco Catalyst 4500X series fixed 10GE aggregation switch with 16 10GE SFP+ ports

cevCat4kWsx4500x32  OBJECT IDENTIFIER
    ::= { cevModuleCat4000Type 57 }

-- Cisco Catalyst 4500X series fixed 10GE aggregation switch with 32 10GE SFP+ ports

cevModuleCVAType  OBJECT IDENTIFIER
    ::= { cevModule 36 }

-- Cisco Voice Adaptar cards

cevCVA122  OBJECT IDENTIFIER
    ::= { cevModuleCVAType 1 }

-- Cisco CVA122 Cable Voice Adapter (Residential Cable Modem with two Voice Ports)

cevCVA124  OBJECT IDENTIFIER
    ::= { cevModuleCVAType 2 }

-- Cisco CVA124 Cable Voice Adapter (Residential Cable Modem with four Voice Ports)

cevCVA122E  OBJECT IDENTIFIER
    ::= { cevModuleCVAType 3 }

-- Cisco CVA122 Cable Voice Adapter (Residential Cable Modem with two voice ports) - European version

cevCVA124E  OBJECT IDENTIFIER
    ::= { cevModuleCVAType 4 }

-- Cisco CVA124 Cable Voice Adapter (Residential Cable Modem with four voice ports) - European version

cevModuleAs5850Type  OBJECT IDENTIFIER
    ::= { cevModule 37 }

cevAs5850EPM2Ge  OBJECT IDENTIFIER
    ::= { cevModuleAs5850Type 1 }

-- Egress Port Module Card with 2 port Gigabit Ethernet for the AS5850 platform

cevAs5850Ct3Up216  OBJECT IDENTIFIER
    ::= { cevModuleAs5850Type 2 }

-- Channelized T3 and  216 Universal Ports Dial Feature Card for the AS5850 platform

cevAs58508Ce1Up216  OBJECT IDENTIFIER
    ::= { cevModuleAs5850Type 3 }

-- 8 port Channelized E1 and  216 Universal Ports Dial Feature Card for the AS5850 platform

cevAs58xxUp324  OBJECT IDENTIFIER
    ::= { cevModuleAs5850Type 4 }

-- 324 Universal Ports Feature Card for the AS5850 platform

cevAs585024E1  OBJECT IDENTIFIER
    ::= { cevModuleAs5850Type 5 }

-- 24 port Channelized E1 Feature Card for the AS5850 platform

cevAs585024T1  OBJECT IDENTIFIER
    ::= { cevModuleAs5850Type 6 }

-- 24 port Channelized T1 Feature Card for the AS5850 platform

cevModuleAs5350Type  OBJECT IDENTIFIER
    ::= { cevModule 38 }

-- Cards that go into the AS5350 series router platform

cevAs5350XMDfcCarrier  OBJECT IDENTIFIER
    ::= { cevModuleAs5350Type 2 }

-- Carrier card that holds Dial Feature Cards for the AS5350-XM carrier

cevModule24xxType  OBJECT IDENTIFIER
    ::= { cevModule 39 }

cevIad2420Vm8fxs  OBJECT IDENTIFIER
    ::= { cevModule24xxType 1 }

-- This card provides 8 analog Foreign eXchange Stations (FXS) in the Integrated Access Device 2420 (IAD2420) chassis

cevIad242016fxs  OBJECT IDENTIFIER
    ::= { cevModule24xxType 2 }

-- This card provides 16 analog Foreign eXchange Stations (FXS) in the Integrated Access Device 2420 (IAD2420) chassis

cevIad2420VmPwr  OBJECT IDENTIFIER
    ::= { cevModule24xxType 3 }

-- This card provides power supply to high density analog FXS voice module in the Integrated Access Device 2420 (IAD2420) chassis

cevIad2420Adsl  OBJECT IDENTIFIER
    ::= { cevModule24xxType 4 }

-- This card provides access to ADSL (Asymmetrical Digital Subscriber Line) over ATM (Asynchronous Transfer Mode) AAL2 (ATM Adaptation Layer 2), AAL5 (ATM Adaptation Layer 5) and various class of QoS (Quality of Service) for both voice and data service on the Integrated Access Device 2420 (IAD2420) chassis

cevIad2420Hcm1  OBJECT IDENTIFIER
    ::= { cevModule24xxType 5 }

-- High performance compression module for the IAD2420 platform equipped with one TI 549 DSP

cevIad2420Hcm2  OBJECT IDENTIFIER
    ::= { cevModule24xxType 6 }

-- High performance compression module for the IAD2420 platform equipped with two TI 549 DSPs

cevIad2420Hcm3  OBJECT IDENTIFIER
    ::= { cevModule24xxType 7 }

-- High performance compression module for the IAD2420 platform equipped with three TI 549 DSPs

cevIad2420Hcm4  OBJECT IDENTIFIER
    ::= { cevModule24xxType 8 }

-- High performance compression module for the IAD2420 platform equipped with four TI 549 DSPs

cevIad2420Hcm5  OBJECT IDENTIFIER
    ::= { cevModule24xxType 9 }

-- High performance compression module for the IAD2420 platform equipped with five TI 549 DSPs

cevIad2420Hcm6  OBJECT IDENTIFIER
    ::= { cevModule24xxType 10 }

-- High performance compression module for the IAD2420 platform equipped with six TI 549 DSPs

cevIad2420Cpu  OBJECT IDENTIFIER
    ::= { cevModule24xxType 11 }

-- CPU card for IAD2420

cevIad2420MfmE1Unbalanced  OBJECT IDENTIFIER
    ::= { cevModule24xxType 12 }

-- IAD2420 E1 75 ohms unbalanced

cevIad2420MfmE1Dsx1Csu  OBJECT IDENTIFIER
    ::= { cevModule24xxType 13 }

-- IAD2420 E1 100/120 ohms balanced

cevIad2420MfmT1Dsx1Csu  OBJECT IDENTIFIER
    ::= { cevModule24xxType 14 }

-- IAD2420 T1 100/120 ohms balanced only

cevIad24208fxo  OBJECT IDENTIFIER
    ::= { cevModule24xxType 15 }

-- High density 8 analog Foreign eXchange Office (FXO) module

cevIad242016fxsOffPremise  OBJECT IDENTIFIER
    ::= { cevModule24xxType 18 }

-- IAD2420 Sixteen FXS Off Premise Analog Voice Module

cevIad2430Ob8Fxs  OBJECT IDENTIFIER
    ::= { cevModule24xxType 19 }

-- This card provides 8 on-board analog Foreign Exchange Stations (FXS) in the Integrated Access Device 2430 (IAD2430) chassis

cevIad2430Ob16Fxs  OBJECT IDENTIFIER
    ::= { cevModule24xxType 20 }

-- This card provides 16 on-board analog Foreign Exchange Stations (FXS) in the Integrated Access Device 2430 (IAD2430) chassis

cevIad2430Ob24Fxs  OBJECT IDENTIFIER
    ::= { cevModule24xxType 21 }

-- This card provides 24 on-board analog Foreign Exchange Stations (FXS) in the Integrated Access Device 2430 (IAD2430) chassis

cevIad2430ObT1E1  OBJECT IDENTIFIER
    ::= { cevModule24xxType 22 }

-- This card provides T1/E1  in the Integrated Access Device 2430 (IAD2430) chassis

cevIad2435ObT1E1  OBJECT IDENTIFIER
    ::= { cevModule24xxType 23 }

-- This card provides T1/E1  in the Integrated Access Device 2435 (IAD2435)

cevIad2435Ob8Fxs  OBJECT IDENTIFIER
    ::= { cevModule24xxType 24 }

-- This card provides 8 on-board analog Foreign Exchange Stations (FXS) in the Integrated Access Device 2435 (IAD2435) chassis

cevVG204Ob4Fxs  OBJECT IDENTIFIER
    ::= { cevModule24xxType 25 }

-- This card provides 4 on-board analog Foreign Exchange Stations (FXS) in the Voice Gateway 204 (VG204) chassis

cevVG202Ob2Fxs  OBJECT IDENTIFIER
    ::= { cevModule24xxType 26 }

-- This card provides 2 on-board analog Foreign Exchange Stations (FXS) in the Voice Gateway 202 (VG202) chassis

cevVg202xmOb2fxs  OBJECT IDENTIFIER
    ::= { cevModule24xxType 27 }

-- This card provides 2 on-board analog Foreign Exchange Stations (FXS) in the Voice Gateway 202xm (VG202XM) chassis

cevVg204xmOb4fxs  OBJECT IDENTIFIER
    ::= { cevModule24xxType 28 }

-- This card provides 4 on-board analog Foreign Exchange Stations (FXS) in the Voice Gateway 204XM (VG204XM) chassis

cevModule10000Bases  OBJECT IDENTIFIER
    ::= { cevModule 40 }

-- Cisco 10 gigabit ethernet port adapter cards

cevM10000BaseLX4  OBJECT IDENTIFIER
    ::= { cevModule10000Bases 2 }

-- Cisco Wide-WDM 1310nm Laser 10 gigabit ethernet port adapter

cevM10000BaseEX4  OBJECT IDENTIFIER
    ::= { cevModule10000Bases 3 }

-- Cisco Wide-WDM 1550nm Laser 10 gigabit ethernet port adapter

cevM10000BaseLR  OBJECT IDENTIFIER
    ::= { cevModule10000Bases 4 }

-- Cisco Serial 1310nm Laser 10 gigabit ethernet port adapter

cevM10000BaseER  OBJECT IDENTIFIER
    ::= { cevModule10000Bases 5 }

-- Cisco Serial 1550nm Laser 10 gigabit ethernet port adapter

cevM10000BaseSX4  OBJECT IDENTIFIER
    ::= { cevModule10000Bases 6 }

-- Cisco Wide-WDM 850nm Laser 10 gigabit ethernet port adapter

cevM10000BaseSR  OBJECT IDENTIFIER
    ::= { cevModule10000Bases 7 }

-- Cisco Serial 850nm Laser 10 gigabit ethernet port adapter

cevM10000BaseCX4  OBJECT IDENTIFIER
    ::= { cevModule10000Bases 8 }

-- Cisco XAUI Copper 10 gigabit ethernet port adapter

cevM10000BaseZR  OBJECT IDENTIFIER
    ::= { cevModule10000Bases 9 }

-- Cisco ZR 1550nm Laser 10 gigabit ethernet port adapter

cev10GBaseLW  OBJECT IDENTIFIER
    ::= { cevModule10000Bases 10 }

-- 10GBASE-LW XENPAK

cev10GBaseEW  OBJECT IDENTIFIER
    ::= { cevModule10000Bases 11 }

-- 10GBASE-EW XENPAK

cev10GBaseSW  OBJECT IDENTIFIER
    ::= { cevModule10000Bases 12 }

-- 10GBASE-SW XENPAK

cev10GBaseEdc1310  OBJECT IDENTIFIER
    ::= { cevModule10000Bases 13 }

-- 10GBase-Serial 1310 nm XENPAK

cev10GBaseDwdm3033  OBJECT IDENTIFIER
    ::= { cevModule10000Bases 14 }

-- 10GBASE-DWDM 1530.33 nm XENPAK

cev10GBaseDwdm3112  OBJECT IDENTIFIER
    ::= { cevModule10000Bases 15 }

-- 10GBASE-DWDM 1531.12 nm XENPAK

cev10GBaseDwdm3190  OBJECT IDENTIFIER
    ::= { cevModule10000Bases 16 }

-- 10GBASE-DWDM 1531.90 nm XENPAK

cev10GBaseDwdm3268  OBJECT IDENTIFIER
    ::= { cevModule10000Bases 17 }

-- 10GBASE-DWDM 1532.68 nm XENPAK

cev10GBaseDwdm3425  OBJECT IDENTIFIER
    ::= { cevModule10000Bases 18 }

-- 10GBASE-DWDM 1534.25 nm XENPAK

cev10GBaseDwdm3504  OBJECT IDENTIFIER
    ::= { cevModule10000Bases 19 }

-- 10GBASE-DWDM 1535.04 nm XENPAK

cev10GBaseDwdm3582  OBJECT IDENTIFIER
    ::= { cevModule10000Bases 20 }

-- 10GBASE-DWDM 1535.82 nm XENPAK

cev10GBaseDwdm3661  OBJECT IDENTIFIER
    ::= { cevModule10000Bases 21 }

-- 10GBASE-DWDM 1536.61 nm XENPAK

cev10GBaseDwdm3819  OBJECT IDENTIFIER
    ::= { cevModule10000Bases 22 }

-- 10GBASE-DWDM 1538.19 nm XENPAK

cev10GBaseDwdm3898  OBJECT IDENTIFIER
    ::= { cevModule10000Bases 23 }

-- 10GBASE-DWDM 1538.98 nm XENPAK

cev10GBaseDwdm3977  OBJECT IDENTIFIER
    ::= { cevModule10000Bases 24 }

-- 10GBASE-DWDM 1539.77 nm XENPAK

cev10GBaseDwdm4056  OBJECT IDENTIFIER
    ::= { cevModule10000Bases 25 }

-- 10GBASE-DWDM 1540.56 nm XENPAK

cev10GBaseDwdm4214  OBJECT IDENTIFIER
    ::= { cevModule10000Bases 26 }

-- 10GBASE-DWDM 1542.14 nm XENPAK

cev10GBaseDwdm4294  OBJECT IDENTIFIER
    ::= { cevModule10000Bases 27 }

-- 10GBASE-DWDM 1542.94 nm XENPAK

cev10GBaseDwdm4373  OBJECT IDENTIFIER
    ::= { cevModule10000Bases 28 }

-- 10GBASE-DWDM 1543.73 nm XENPAK

cev10GBaseDwdm4453  OBJECT IDENTIFIER
    ::= { cevModule10000Bases 29 }

-- 10GBASE-DWDM 1544.53 nm XENPAK

cev10GBaseDwdm4612  OBJECT IDENTIFIER
    ::= { cevModule10000Bases 30 }

-- 10GBASE-DWDM 1546.12 nm XENPAK

cev10GBaseDwdm4692  OBJECT IDENTIFIER
    ::= { cevModule10000Bases 31 }

-- 10GBASE-DWDM 1546.92 nm XENPAK

cev10GBaseDwdm4772  OBJECT IDENTIFIER
    ::= { cevModule10000Bases 32 }

-- 10GBASE-DWDM 1547.72 nm XENPAK

cev10GBaseDwdm4851  OBJECT IDENTIFIER
    ::= { cevModule10000Bases 33 }

-- 10GBASE-DWDM 1548.51 nm XENPAK

cev10GBaseDwdm5012  OBJECT IDENTIFIER
    ::= { cevModule10000Bases 34 }

-- 10GBASE-DWDM 1550.12 nm XENPAK

cev10GBaseDwdm5092  OBJECT IDENTIFIER
    ::= { cevModule10000Bases 35 }

-- 10GBASE-DWDM 1550.92 nm XENPAK

cev10GBaseDwdm5172  OBJECT IDENTIFIER
    ::= { cevModule10000Bases 36 }

-- 10GBASE-DWDM 1551.72 nm XENPAK

cev10GBaseDwdm5252  OBJECT IDENTIFIER
    ::= { cevModule10000Bases 37 }

-- 10GBASE-DWDM 1552.52 nm XENPAK

cev10GBaseDwdm5413  OBJECT IDENTIFIER
    ::= { cevModule10000Bases 38 }

-- 10GBASE-DWDM 1554.13 nm XENPAK

cev10GBaseDwdm5494  OBJECT IDENTIFIER
    ::= { cevModule10000Bases 39 }

-- 10GBASE-DWDM 1554.94 nm XENPAK

cev10GBaseDwdm5575  OBJECT IDENTIFIER
    ::= { cevModule10000Bases 40 }

-- 10GBASE-DWDM 1555.75 nm XENPAK

cev10GBaseDwdm5655  OBJECT IDENTIFIER
    ::= { cevModule10000Bases 41 }

-- 10GBASE-DWDM 1556.55 nm XENPAK

cev10GBaseDwdm5817  OBJECT IDENTIFIER
    ::= { cevModule10000Bases 42 }

-- 10GBASE-DWDM 1558.17 nm XENPAK

cev10GBaseDwdm5898  OBJECT IDENTIFIER
    ::= { cevModule10000Bases 43 }

-- 10GBASE-DWDM 1558.98 nm XENPAK

cev10GBaseDwdm5979  OBJECT IDENTIFIER
    ::= { cevModule10000Bases 44 }

-- 10GBASE-DWDM 1559.79 nm XENPAK

cev10GBaseDwdm6061  OBJECT IDENTIFIER
    ::= { cevModule10000Bases 45 }

-- 10GBASE-DWDM 1560.61 nm XENPAK

cev10GBaseRec  OBJECT IDENTIFIER
    ::= { cevModule10000Bases 46 }

-- 10GBASE-WDM receive-only XENPAK

cevModuleONS15540Type  OBJECT IDENTIFIER
    ::= { cevModule 42 }

-- Cisco ONS 15540 ESP Modules

cevONS15540LCMBTspProtect  OBJECT IDENTIFIER
    ::= { cevModuleONS15540Type 1 }

-- Cisco ONS 15540 ESP transponder motherboard for 4 Type I & II transponders with splitter protection

cevONS15540LCMBTspEast  OBJECT IDENTIFIER
    ::= { cevModuleONS15540Type 2 }

-- Cisco ONS 15540 ESP transponder motherboard for 4 Type I & II transponders without protection - East

cevONS15540LCMBTspWest  OBJECT IDENTIFIER
    ::= { cevModuleONS15540Type 3 }

-- Cisco ONS 15540 ESP transponder motherboard for 4 Type I & II transponders without protection - West

cevONS15540MDXMBOSC  OBJECT IDENTIFIER
    ::= { cevModuleONS15540Type 4 }

-- Cisco ONS 15540 ESP Mux/Demux Motherboard with OSC

cevONS15540MDXMB  OBJECT IDENTIFIER
    ::= { cevModuleONS15540Type 5 }

-- Cisco ONS 15540 ESP Mux/Demux Motherboard without OSC

cevONS15540Tsp1Ch0102MmSc  OBJECT IDENTIFIER
    ::= { cevModuleONS15540Type 6 }

-- Transponder Type I, channel 1 or 2,  1310-nm MM, SC connector

cevONS15540Tsp1Ch0304MmSc  OBJECT IDENTIFIER
    ::= { cevModuleONS15540Type 7 }

-- Transponder Type I, channel 3 or 4, 1310-nm MM, SC connector

cevONS15540Tsp1Ch0506MmSc  OBJECT IDENTIFIER
    ::= { cevModuleONS15540Type 8 }

-- Transponder Type I, channel 5 or 6, 1310-nm MM, SC connector

cevONS15540Tsp1Ch0708MmSc  OBJECT IDENTIFIER
    ::= { cevModuleONS15540Type 9 }

-- Transponder Type I, channel 7 or 8, 1310-nm MM, SC connector

cevONS15540Tsp1Ch0910MmSc  OBJECT IDENTIFIER
    ::= { cevModuleONS15540Type 10 }

-- Transponder Type I, channel 9 or 10, 1310-nm MM, SC connector

cevONS15540Tsp1Ch1112MmSc  OBJECT IDENTIFIER
    ::= { cevModuleONS15540Type 11 }

-- Transponder Type I, channel 11 or 12, 1310-nm MM, SC connector

cevONS15540Tsp1Ch1314MmSc  OBJECT IDENTIFIER
    ::= { cevModuleONS15540Type 12 }

-- Transponder Type I, channel 13 or 14, 1310-nm MM, SC connector

cevONS15540Tsp1Ch1516MmSc  OBJECT IDENTIFIER
    ::= { cevModuleONS15540Type 13 }

-- Transponder Type I, channel 15 or 16, 1310-nm MM, SC connector

cevONS15540Tsp1Ch1718MmSc  OBJECT IDENTIFIER
    ::= { cevModuleONS15540Type 14 }

-- Transponder Type I, channel 17 or 18, 1310-nm MM, SC connector

cevONS15540Tsp1Ch1920MmSc  OBJECT IDENTIFIER
    ::= { cevModuleONS15540Type 15 }

-- Transponder Type I, channel 19 or 20, 1310-nm MM, SC connector

cevONS15540Tsp1Ch2122MmSc  OBJECT IDENTIFIER
    ::= { cevModuleONS15540Type 16 }

-- Transponder Type I, channel 21 or 22, 1310-nm MM, SC connector

cevONS15540Tsp1Ch2324MmSc  OBJECT IDENTIFIER
    ::= { cevModuleONS15540Type 17 }

-- Transponder Type I, channel 23 or 24, 1310-nm MM, SC connector

cevONS15540Tsp1Ch2526MmSc  OBJECT IDENTIFIER
    ::= { cevModuleONS15540Type 18 }

-- Transponder Type I, channel 25 or 26, 1310-nm MM, SC connector

cevONS15540Tsp1Ch2728MmSc  OBJECT IDENTIFIER
    ::= { cevModuleONS15540Type 19 }

-- Transponder Type I, channel 27 or 28, 1310-nm MM, SC connector

cevONS15540Tsp1Ch2930MmSc  OBJECT IDENTIFIER
    ::= { cevModuleONS15540Type 20 }

-- Transponder Type I, channel 29 or 30, 1310-nm MM, SC connector

cevONS15540Tsp1Ch3132MmSc  OBJECT IDENTIFIER
    ::= { cevModuleONS15540Type 21 }

-- Transponder Type I, channel 31 or 32, 1310-nm MM, SC connector

cevONS15540Tsp1Ch0102SmSc  OBJECT IDENTIFIER
    ::= { cevModuleONS15540Type 22 }

-- Transponder Type I, channel 1 or 2, 1310-nm SM, SC connector

cevONS15540Tsp1Ch0304SmSc  OBJECT IDENTIFIER
    ::= { cevModuleONS15540Type 23 }

-- Transponder Type I, channel 3 or 4, 1310-nm SM, SC connector

cevONS15540Tsp1Ch0506SmSc  OBJECT IDENTIFIER
    ::= { cevModuleONS15540Type 24 }

-- Transponder Type I, channel 5 or 6, 1310-nm SM, SC connector

cevONS15540Tsp1Ch0708SmSc  OBJECT IDENTIFIER
    ::= { cevModuleONS15540Type 25 }

-- Transponder Type I, channel 7 or 8, 1310-nm SM, SC connector

cevONS15540Tsp1Ch0910SmSc  OBJECT IDENTIFIER
    ::= { cevModuleONS15540Type 26 }

-- Transponder Type I, channel 9 or 10, 1310-nm SM, SC connector

cevONS15540Tsp1Ch1112SmSc  OBJECT IDENTIFIER
    ::= { cevModuleONS15540Type 27 }

-- Transponder Type I, channel 11 or 12, 1310-nm SM, SC connector

cevONS15540Tsp1Ch1314SmSc  OBJECT IDENTIFIER
    ::= { cevModuleONS15540Type 28 }

-- Transponder Type I, channel 13 or 14, 1310-nm SM, SC connector

cevONS15540Tsp1Ch1516SmSc  OBJECT IDENTIFIER
    ::= { cevModuleONS15540Type 29 }

-- Transponder Type I, channel 15 or 16, 1310-nm SM, SC connector

cevONS15540Tsp1Ch1718SmSc  OBJECT IDENTIFIER
    ::= { cevModuleONS15540Type 30 }

-- Transponder Type I, channel 17 or 18, 1310-nm SM, SC connector

cevONS15540Tsp1Ch1920SmSc  OBJECT IDENTIFIER
    ::= { cevModuleONS15540Type 31 }

-- Transponder Type I, channel 19 or 20, 1310-nm SM, SC connector

cevONS15540Tsp1Ch2122SmSc  OBJECT IDENTIFIER
    ::= { cevModuleONS15540Type 32 }

-- Transponder Type I, channel 21 or 22, 1310-nm SM, SC connector

cevONS15540Tsp1Ch2324SmSc  OBJECT IDENTIFIER
    ::= { cevModuleONS15540Type 33 }

-- Transponder Type I, channel 23 or 24, 1310-nm SM, SC connector

cevONS15540Tsp1Ch2526SmSc  OBJECT IDENTIFIER
    ::= { cevModuleONS15540Type 34 }

-- Transponder Type I, channel 25 or 26, 1310-nm SM, SC connector

cevONS15540Tsp1Ch2728SmSc  OBJECT IDENTIFIER
    ::= { cevModuleONS15540Type 35 }

-- Transponder Type I, channel 27 or 28, 1310-nm SM, SC connector

cevONS15540Tsp1Ch2930SmSc  OBJECT IDENTIFIER
    ::= { cevModuleONS15540Type 36 }

-- Transponder Type I, channel 29 or 30, 1310-nm SM, SC connector

cevONS15540Tsp1Ch3132SmSc  OBJECT IDENTIFIER
    ::= { cevModuleONS15540Type 37 }

-- Transponder Type I, channel 31 or 32, 1310-nm SM, SC connector

cevONS15540MDX4ChA  OBJECT IDENTIFIER
    ::= { cevModuleONS15540Type 38 }

-- 4-channel optical add/drop mux/demux, band A, without OSC

cevONS15540MDX4ChB  OBJECT IDENTIFIER
    ::= { cevModuleONS15540Type 39 }

-- 4-channel optical add/drop mux/demux, band B, without OSC

cevONS15540MDX4ChC  OBJECT IDENTIFIER
    ::= { cevModuleONS15540Type 40 }

-- 4-channel optical add/drop mux/demux, band C, without OSC

cevONS15540MDX4ChD  OBJECT IDENTIFIER
    ::= { cevModuleONS15540Type 41 }

-- 4-channel optical add/drop mux/demux, band D, without OSC

cevONS15540MDX4ChE  OBJECT IDENTIFIER
    ::= { cevModuleONS15540Type 42 }

-- 4-channel optical add/drop mux/demux, band E, without OSC

cevONS15540MDX4ChF  OBJECT IDENTIFIER
    ::= { cevModuleONS15540Type 43 }

-- 4-channel optical add/drop mux/demux, band F, without OSC

cevONS15540MDX4ChG  OBJECT IDENTIFIER
    ::= { cevModuleONS15540Type 44 }

-- 4-channel optical add/drop mux/demux, band G, without OSC

cevONS15540MDX4ChH  OBJECT IDENTIFIER
    ::= { cevModuleONS15540Type 45 }

-- 4-channel optical add/drop mux/demux, band H, without OSC

cevONS15540MDX8ChAB  OBJECT IDENTIFIER
    ::= { cevModuleONS15540Type 46 }

-- 8-channel optical add/drop mux/demux, band AB, without OSC

cevONS15540MDX8ChCD  OBJECT IDENTIFIER
    ::= { cevModuleONS15540Type 47 }

-- 8-channel optical add/drop mux/demux, band CD, without OSC

cevONS15540MDX8ChEF  OBJECT IDENTIFIER
    ::= { cevModuleONS15540Type 48 }

-- 8-channel optical add/drop mux/demux, band EF, without OSC

cevONS15540MDX8ChGH  OBJECT IDENTIFIER
    ::= { cevModuleONS15540Type 49 }

-- 8-channel optical add/drop mux/demux, band GH, without OSC

cevONS15540MDX4ChAOSC  OBJECT IDENTIFIER
    ::= { cevModuleONS15540Type 50 }

-- 4-channel optical add/drop mux/demux, band A, with OSC

cevONS15540MDX4ChBOSC  OBJECT IDENTIFIER
    ::= { cevModuleONS15540Type 51 }

-- 4-channel optical add/drop mux/demux, band B, with OSC

cevONS15540MDX4ChCOSC  OBJECT IDENTIFIER
    ::= { cevModuleONS15540Type 52 }

-- 4-channel optical add/drop mux/demux, band C, with OSC

cevONS15540MDX4ChDOSC  OBJECT IDENTIFIER
    ::= { cevModuleONS15540Type 53 }

-- 4-channel optical add/drop mux/demux, band D, with OSC

cevONS15540MDX4ChEOSC  OBJECT IDENTIFIER
    ::= { cevModuleONS15540Type 54 }

-- 4-channel optical add/drop mux/demux, band E, with OSC

cevONS15540MDX4ChFOSC  OBJECT IDENTIFIER
    ::= { cevModuleONS15540Type 55 }

-- 4-channel optical add/drop mux/demux, band F, with OSC

cevONS15540MDX4ChGOSC  OBJECT IDENTIFIER
    ::= { cevModuleONS15540Type 56 }

-- 4-channel optical add/drop mux/demux, band G, with OSC

cevONS15540MDX4ChHOSC  OBJECT IDENTIFIER
    ::= { cevModuleONS15540Type 57 }

-- 4-channel optical add/drop mux/demux, band H, with OSC

cevONS15540MDX8ChABOSC  OBJECT IDENTIFIER
    ::= { cevModuleONS15540Type 58 }

-- 8-channel optical add/drop mux/demux, band AB, with OSC

cevONS15540MDX8ChCDOSC  OBJECT IDENTIFIER
    ::= { cevModuleONS15540Type 59 }

-- 8-channel optical add/drop mux/demux, band CD, with OSC

cevONS15540MDX8ChEFOSC  OBJECT IDENTIFIER
    ::= { cevModuleONS15540Type 60 }

-- 8-channel optical add/drop mux/demux, band EF, with OSC

cevONS15540MDX8ChGHOSC  OBJECT IDENTIFIER
    ::= { cevModuleONS15540Type 61 }

-- 8-channel optical add/drop mux/demux, band GH, with OSC

cevONS15540MDX16ChADOSC  OBJECT IDENTIFIER
    ::= { cevModuleONS15540Type 62 }

-- 16-channel optical terminal mux/demux, band AD, with OSC

cevONS15540MDX16ChEH  OBJECT IDENTIFIER
    ::= { cevModuleONS15540Type 63 }

-- 16-channel optical terminal mux/demux, band EH, without OSC

cevONS15540Tsp2Ch0102  OBJECT IDENTIFIER
    ::= { cevModuleONS15540Type 64 }

-- Transponder Type II Ch 1/2

cevONS15540Tsp2Ch0304  OBJECT IDENTIFIER
    ::= { cevModuleONS15540Type 65 }

-- Transponder Type II Ch 3/4

cevONS15540Tsp2Ch0506  OBJECT IDENTIFIER
    ::= { cevModuleONS15540Type 66 }

-- Transponder Type II Ch 5/6

cevONS15540Tsp2Ch0708  OBJECT IDENTIFIER
    ::= { cevModuleONS15540Type 67 }

-- Transponder Type II Ch 7/8

cevONS15540Tsp2Ch0910  OBJECT IDENTIFIER
    ::= { cevModuleONS15540Type 68 }

-- Transponder Type II Ch 9/10

cevONS15540Tsp2Ch1112  OBJECT IDENTIFIER
    ::= { cevModuleONS15540Type 69 }

-- Transponder Type II Ch 11/12

cevONS15540Tsp2Ch1314  OBJECT IDENTIFIER
    ::= { cevModuleONS15540Type 70 }

-- Transponder Type II Ch 13/14

cevONS15540Tsp2Ch1516  OBJECT IDENTIFIER
    ::= { cevModuleONS15540Type 71 }

-- Transponder Type II Ch 15/16

cevONS15540Tsp2Ch1718  OBJECT IDENTIFIER
    ::= { cevModuleONS15540Type 72 }

-- Transponder Type II Ch 17/18

cevONS15540Tsp2Ch1920  OBJECT IDENTIFIER
    ::= { cevModuleONS15540Type 73 }

-- Transponder Type II Ch 19/20

cevONS15540Tsp2Ch2122  OBJECT IDENTIFIER
    ::= { cevModuleONS15540Type 74 }

-- Transponder Type II Ch 21/22

cevONS15540Tsp2Ch2324  OBJECT IDENTIFIER
    ::= { cevModuleONS15540Type 75 }

-- Transponder Type II Ch 23/24

cevONS15540Tsp2Ch2526  OBJECT IDENTIFIER
    ::= { cevModuleONS15540Type 76 }

-- Transponder Type II Ch 25/26

cevONS15540Tsp2Ch2728  OBJECT IDENTIFIER
    ::= { cevModuleONS15540Type 77 }

-- Transponder Type II Ch 27/28

cevONS15540Tsp2Ch2930  OBJECT IDENTIFIER
    ::= { cevModuleONS15540Type 78 }

-- Transponder Type II Ch 29/30

cevONS15540Tsp2Ch3132  OBJECT IDENTIFIER
    ::= { cevModuleONS15540Type 79 }

-- Transponder Type II Ch 31/32

cevONS15540LCMB10GOC192c  OBJECT IDENTIFIER
    ::= { cevModuleONS15540Type 80 }

-- ONS 15540 ESP LineCard motherboard - Supports 2 10GE/OC192c Modules without Splitter

cevONS15540ESPxLCMBTspSp  OBJECT IDENTIFIER
    ::= { cevModuleONS15540Type 81 }

-- ONS 15540 ESPx LineCard Motherboard with Splitter - Supports 4 Type I and II Transponders

cevONS15540ESPxLCMBTsp  OBJECT IDENTIFIER
    ::= { cevModuleONS15540Type 82 }

-- ONS 15540 ESPx LineCard Motherboard with Splitter - Supports 4 Type I and II Transponders

cevONS15540ESPxLCMB10GOC192cSp  OBJECT IDENTIFIER
    ::= { cevModuleONS15540Type 83 }

-- ONS 15540 ESPx LineCard Motherboard with Splitter - Supports 2 10GE/OC192c Transponders

cevONS15540ESPxLCMB10GOC192c  OBJECT IDENTIFIER
    ::= { cevModuleONS15540Type 84 }

-- ONS 15540 ESPx LineCard Motherboard without Splitter - Supports 2 10GE/OC192c Transponders

cevONS15540LCDC10G  OBJECT IDENTIFIER
    ::= { cevModuleONS15540Type 85 }

-- ONS 15540 ESP - 10GE/OC192 Adaptor Daughter Card

cevONS15540ESPxMDXMBOsc  OBJECT IDENTIFIER
    ::= { cevModuleONS15540Type 86 }

-- ONS 15540 ESPx Mux/Demux Motherboard with OSC

cevONS15540ESPxMDXMB  OBJECT IDENTIFIER
    ::= { cevModuleONS15540Type 87 }

-- ONS 15540 ESPx Mux/Demux Motherboard without OSC

cevONS15540ESPxMDXMBOscESP  OBJECT IDENTIFIER
    ::= { cevModuleONS15540Type 88 }

-- ONS 15540 ESPx Motherboard with OSC - Supports 15540 ESP Mux/Demux modules

cevONS15540ESPxMDXMBESP  OBJECT IDENTIFIER
    ::= { cevModuleONS15540Type 89 }

-- ONS 15540 ESPx Motherboard without OSC - Support 15540 ESP Mux/Demux modules

cevONS1554010GigITUCh01  OBJECT IDENTIFIER
    ::= { cevModuleONS15540Type 90 }

-- 10GE card - 1310nm SM Client interface with SC and ITU Laser Channel 1

cevONS1554010GigITUCh02  OBJECT IDENTIFIER
    ::= { cevModuleONS15540Type 91 }

-- 10GE card - 1310nm SM Client interface with SC and ITU Laser Channel 2

cevONS1554010GigITUCh03  OBJECT IDENTIFIER
    ::= { cevModuleONS15540Type 92 }

-- 10GE card - 1310nm SM Client interface with SC and ITU Laser Channel 3

cevONS1554010GigITUCh04  OBJECT IDENTIFIER
    ::= { cevModuleONS15540Type 93 }

-- 10GE card - 1310nm SM Client interface with SC and ITU Laser Channel 4

cevONS1554010GigITUCh05  OBJECT IDENTIFIER
    ::= { cevModuleONS15540Type 94 }

-- 10GE card - 1310nm SM Client interface with SC and ITU Laser Channel 5

cevONS1554010GigITUCh06  OBJECT IDENTIFIER
    ::= { cevModuleONS15540Type 95 }

-- 10GE card - 1310nm SM Client interface with SC and ITU Laser Channel 6

cevONS1554010GigITUCh07  OBJECT IDENTIFIER
    ::= { cevModuleONS15540Type 96 }

-- 10GE card - 1310nm SM Client interface with SC and ITU Laser Channel 7

cevONS1554010GigITUCh08  OBJECT IDENTIFIER
    ::= { cevModuleONS15540Type 97 }

-- 10GE card - 1310nm SM Client interface with SC and ITU Laser Channel 8

cevONS1554010GigITUCh09  OBJECT IDENTIFIER
    ::= { cevModuleONS15540Type 98 }

-- 10GE card - 1310nm SM Client interface with SC and ITU Laser Channel 9

cevONS1554010GigITUCh10  OBJECT IDENTIFIER
    ::= { cevModuleONS15540Type 99 }

-- 10GE card - 1310nm SM Client interface with SC and ITU Laser Channel 10

cevONS1554010GigITUCh11  OBJECT IDENTIFIER
    ::= { cevModuleONS15540Type 100 }

-- 10GE card - 1310nm SM Client interface with SC and ITU Laser Channel 11

cevONS1554010GigITUCh12  OBJECT IDENTIFIER
    ::= { cevModuleONS15540Type 101 }

-- 10GE card - 1310nm SM Client interface with SC and ITU Laser Channel 12

cevONS1554010GigITUCh13  OBJECT IDENTIFIER
    ::= { cevModuleONS15540Type 102 }

-- 10GE card - 1310nm SM Client interface with SC and ITU Laser Channel 13

cevONS1554010GigITUCh14  OBJECT IDENTIFIER
    ::= { cevModuleONS15540Type 103 }

-- 10GE card - 1310nm SM Client interface with SC and ITU Laser Channel 14

cevONS1554010GigITUCh15  OBJECT IDENTIFIER
    ::= { cevModuleONS15540Type 104 }

-- 10GE card - 1310nm SM Client interface with SC and ITU Laser Channel 15

cevONS1554010GigITUCh16  OBJECT IDENTIFIER
    ::= { cevModuleONS15540Type 105 }

-- 10GE card - 1310nm SM Client interface with SC and ITU Laser Channel 16

cevONS1554010GigITUCh17  OBJECT IDENTIFIER
    ::= { cevModuleONS15540Type 106 }

-- 10GE card - 1310nm SM Client interface with SC and ITU Laser Channel 17

cevONS1554010GigITUCh18  OBJECT IDENTIFIER
    ::= { cevModuleONS15540Type 107 }

-- 10GE card - 1310nm SM Client interface with SC and ITU Laser Channel 18

cevONS1554010GigITUCh19  OBJECT IDENTIFIER
    ::= { cevModuleONS15540Type 108 }

-- 10GE card - 1310nm SM Client interface with SC and ITU Laser Channel 19

cevONS1554010GigITUCh20  OBJECT IDENTIFIER
    ::= { cevModuleONS15540Type 109 }

-- 10GE card - 1310nm SM Client interface with SC and ITU Laser Channel 20

cevONS1554010GigITUCh21  OBJECT IDENTIFIER
    ::= { cevModuleONS15540Type 110 }

-- 10GE card - 1310nm SM Client interface with SC and ITU Laser Channel 21

cevONS1554010GigITUCh22  OBJECT IDENTIFIER
    ::= { cevModuleONS15540Type 111 }

-- 10GE card - 1310nm SM Client interface with SC and ITU Laser Channel 22

cevONS1554010GigITUCh23  OBJECT IDENTIFIER
    ::= { cevModuleONS15540Type 112 }

-- 10GE card - 1310nm SM Client interface with SC and ITU Laser Channel 23

cevONS1554010GigITUCh24  OBJECT IDENTIFIER
    ::= { cevModuleONS15540Type 113 }

-- 10GE card - 1310nm SM Client interface with SC and ITU Laser Channel 24

cevONS1554010GigITUCh25  OBJECT IDENTIFIER
    ::= { cevModuleONS15540Type 114 }

-- 10GE card - 1310nm SM Client interface with SC and ITU Laser Channel 25

cevONS1554010GigITUCh26  OBJECT IDENTIFIER
    ::= { cevModuleONS15540Type 115 }

-- 10GE card - 1310nm SM Client interface with SC and ITU Laser Channel 26

cevONS1554010GigITUCh27  OBJECT IDENTIFIER
    ::= { cevModuleONS15540Type 116 }

-- 10GE card - 1310nm SM Client interface with SC and ITU Laser Channel 27

cevONS1554010GigITUCh28  OBJECT IDENTIFIER
    ::= { cevModuleONS15540Type 117 }

-- 10GE card - 1310nm SM Client interface with SC and ITU Laser Channel 28

cevONS1554010GigITUCh29  OBJECT IDENTIFIER
    ::= { cevModuleONS15540Type 118 }

-- 10GE card - 1310nm SM Client interface with SC and ITU Laser Channel 29

cevONS1554010GigITUCh30  OBJECT IDENTIFIER
    ::= { cevModuleONS15540Type 119 }

-- 10GE card - 1310nm SM Client interface with SC and ITU Laser Channel 30

cevONS1554010GigITUCh31  OBJECT IDENTIFIER
    ::= { cevModuleONS15540Type 120 }

-- 10GE card - 1310nm SM Client interface with SC and ITU Laser Channel 31

cevONS1554010GigITUCh32  OBJECT IDENTIFIER
    ::= { cevModuleONS15540Type 121 }

-- 10GE card - 1310nm SM Client interface with SC and ITU Laser Channel 32

cevONS15540OC192cITUCh01  OBJECT IDENTIFIER
    ::= { cevModuleONS15540Type 122 }

-- OC 192c card - 1310nm SM Client interface with SC and ITU Laser Channel 1

cevONS15540OC192cITUCh02  OBJECT IDENTIFIER
    ::= { cevModuleONS15540Type 123 }

-- OC 192c card - 1310nm SM Client interface with SC and ITU Laser Channel 2

cevONS15540OC192cITUCh03  OBJECT IDENTIFIER
    ::= { cevModuleONS15540Type 124 }

-- OC 192c card - 1310nm SM Client interface with SC and ITU Laser Channel 3

cevONS15540OC192cITUCh04  OBJECT IDENTIFIER
    ::= { cevModuleONS15540Type 125 }

-- OC 192c card - 1310nm SM Client interface with SC and ITU Laser Channel 4

cevONS15540OC192cITUCh05  OBJECT IDENTIFIER
    ::= { cevModuleONS15540Type 126 }

-- OC 192c card - 1310nm SM Client interface with SC and ITU Laser Channel 5

cevONS15540OC192cITUCh06  OBJECT IDENTIFIER
    ::= { cevModuleONS15540Type 127 }

-- OC 192c card - 1310nm SM Client interface with SC and ITU Laser Channel 6

cevONS15540OC192cITUCh07  OBJECT IDENTIFIER
    ::= { cevModuleONS15540Type 128 }

-- OC 192c card - 1310nm SM Client interface with SC and ITU Laser Channel 7

cevONS15540OC192cITUCh08  OBJECT IDENTIFIER
    ::= { cevModuleONS15540Type 129 }

-- OC 192c card - 1310nm SM Client interface with SC and ITU Laser Channel 8

cevONS15540OC192cITUCh09  OBJECT IDENTIFIER
    ::= { cevModuleONS15540Type 130 }

-- OC 192c card - 1310nm SM Client interface with SC and ITU Laser Channel 9

cevONS15540OC192cITUCh10  OBJECT IDENTIFIER
    ::= { cevModuleONS15540Type 131 }

-- OC 192c card - 1310nm SM Client interface with SC and ITU Laser Channel 10

cevONS15540OC192cITUCh11  OBJECT IDENTIFIER
    ::= { cevModuleONS15540Type 132 }

-- OC 192c card - 1310nm SM Client interface with SC and ITU Laser Channel 11

cevONS15540OC192cITUCh12  OBJECT IDENTIFIER
    ::= { cevModuleONS15540Type 133 }

-- OC 192c card - 1310nm SM Client interface with SC and ITU Laser Channel 12

cevONS15540OC192cITUCh13  OBJECT IDENTIFIER
    ::= { cevModuleONS15540Type 134 }

-- OC 192c card - 1310nm SM Client interface with SC and ITU Laser Channel 13

cevONS15540OC192cITUCh14  OBJECT IDENTIFIER
    ::= { cevModuleONS15540Type 135 }

-- OC 192c card - 1310nm SM Client interface with SC and ITU Laser Channel 14

cevONS15540OC192cITUCh15  OBJECT IDENTIFIER
    ::= { cevModuleONS15540Type 136 }

-- OC 192c card - 1310nm SM Client interface with SC and ITU Laser Channel 15

cevONS15540OC192cITUCh16  OBJECT IDENTIFIER
    ::= { cevModuleONS15540Type 137 }

-- OC 192c card - 1310nm SM Client interface with SC and ITU Laser Channel 16

cevONS15540OC192cITUCh17  OBJECT IDENTIFIER
    ::= { cevModuleONS15540Type 138 }

-- OC 192c card - 1310nm SM Client interface with SC and ITU Laser Channel 17

cevONS15540OC192cITUCh18  OBJECT IDENTIFIER
    ::= { cevModuleONS15540Type 139 }

-- OC 192c card - 1310nm SM Client interface with SC and ITU Laser Channel 18

cevONS15540OC192cITUCh19  OBJECT IDENTIFIER
    ::= { cevModuleONS15540Type 140 }

-- OC 192c card - 1310nm SM Client interface with SC and ITU Laser Channel 19

cevONS15540OC192cITUCh20  OBJECT IDENTIFIER
    ::= { cevModuleONS15540Type 141 }

-- OC 192c card - 1310nm SM Client interface with SC and ITU Laser Channel 20

cevONS15540OC192cITUCh21  OBJECT IDENTIFIER
    ::= { cevModuleONS15540Type 142 }

-- OC 192c card - 1310nm SM Client interface with SC and ITU Laser Channel 21

cevONS15540OC192cITUCh22  OBJECT IDENTIFIER
    ::= { cevModuleONS15540Type 143 }

-- OC 192c card - 1310nm SM Client interface with SC and ITU Laser Channel 22

cevONS15540OC192cITUCh23  OBJECT IDENTIFIER
    ::= { cevModuleONS15540Type 144 }

-- OC 192c card - 1310nm SM Client interface with SC and ITU Laser Channel 23

cevONS15540OC192cITUCh24  OBJECT IDENTIFIER
    ::= { cevModuleONS15540Type 145 }

-- OC 192c card - 1310nm SM Client interface with SC and ITU Laser Channel 24

cevONS15540OC192cITUCh25  OBJECT IDENTIFIER
    ::= { cevModuleONS15540Type 146 }

-- OC 192c card - 1310nm SM Client interface with SC and ITU Laser Channel 25

cevONS15540OC192cITUCh26  OBJECT IDENTIFIER
    ::= { cevModuleONS15540Type 147 }

-- OC 192c card - 1310nm SM Client interface with SC and ITU Laser Channel 26

cevONS15540OC192cITUCh27  OBJECT IDENTIFIER
    ::= { cevModuleONS15540Type 148 }

-- OC 192c card - 1310nm SM Client interface with SC and ITU Laser Channel 27

cevONS15540OC192cITUCh28  OBJECT IDENTIFIER
    ::= { cevModuleONS15540Type 149 }

-- OC 192c card - 1310nm SM Client interface with SC and ITU Laser Channel 28

cevONS15540OC192cITUCh29  OBJECT IDENTIFIER
    ::= { cevModuleONS15540Type 150 }

-- OC 192c card - 1310nm SM Client interface with SC and ITU Laser Channel 29

cevONS15540OC192cITUCh30  OBJECT IDENTIFIER
    ::= { cevModuleONS15540Type 151 }

-- OC 192c card - 1310nm SM Client interface with SC and ITU Laser Channel 30

cevONS15540OC192cITUCh31  OBJECT IDENTIFIER
    ::= { cevModuleONS15540Type 152 }

-- OC 192c card - 1310nm SM Client interface with SC and ITU Laser Channel 31

cevONS15540OC192cITUCh32  OBJECT IDENTIFIER
    ::= { cevModuleONS15540Type 153 }

-- OC 192c card - 1310nm SM Client interface with SC and ITU Laser Channel 32

cevONS15540ESPxMDX4ChA  OBJECT IDENTIFIER
    ::= { cevModuleONS15540Type 154 }

-- ONS 15540 ESPx - 4 Channel Mux/Demux, Band A without OSC

cevONS15540ESPxMDX4ChB  OBJECT IDENTIFIER
    ::= { cevModuleONS15540Type 155 }

-- ONS 15540 ESPx - 4 Channel Mux/Demux, Band B without OSC

cevONS15540ESPxMDX4ChC  OBJECT IDENTIFIER
    ::= { cevModuleONS15540Type 156 }

-- ONS 15540 ESPx - 4 Channel Mux/Demux, Band C without OSC

cevONS15540ESPxMDX4ChD  OBJECT IDENTIFIER
    ::= { cevModuleONS15540Type 157 }

-- ONS 15540 ESPx - 4 Channel Mux/Demux, Band D without OSC

cevONS15540ESPxMDX4ChE  OBJECT IDENTIFIER
    ::= { cevModuleONS15540Type 158 }

-- ONS 15540 ESPx - 4 Channel Mux/Demux, Band E without OSC

cevONS15540ESPxMDX4ChF  OBJECT IDENTIFIER
    ::= { cevModuleONS15540Type 159 }

-- ONS 15540 ESPx - 4 Channel Mux/Demux, Band F without OSC

cevONS15540ESPxMDX4ChG  OBJECT IDENTIFIER
    ::= { cevModuleONS15540Type 160 }

-- ONS 15540 ESPx - 4 Channel Mux/Demux, Band G without OSC

cevONS15540ESPxMDX4ChH  OBJECT IDENTIFIER
    ::= { cevModuleONS15540Type 161 }

-- ONS 15540 ESPx - 4 Channel Mux/Demux, Band H without OSC

cevONS15540ESPxMDX8ChAB  OBJECT IDENTIFIER
    ::= { cevModuleONS15540Type 162 }

-- ONS 15540 ESPx - 8 Channel Mux/Demux, Band AB without OSC

cevONS15540ESPxMDX8ChCD  OBJECT IDENTIFIER
    ::= { cevModuleONS15540Type 163 }

-- ONS 15540 ESPx - 8 Channel Mux/Demux, Band CD without OSC

cevONS15540ESPxMDX8ChEF  OBJECT IDENTIFIER
    ::= { cevModuleONS15540Type 164 }

-- ONS 15540 ESPx - 8 Channel Mux/Demux, Band EF without OSC

cevONS15540ESPxMDX8ChGH  OBJECT IDENTIFIER
    ::= { cevModuleONS15540Type 165 }

-- ONS 15540 ESPx - 8 Channel Mux/Demux, Band GH without OSC

cevONS15540ESPxMDX16ChEH  OBJECT IDENTIFIER
    ::= { cevModuleONS15540Type 166 }

-- ONS 15540 ESPx - 16 Channel Mux/Demux, Band EH without OSC

cevONS15540ESPxMDX4ChAOSC  OBJECT IDENTIFIER
    ::= { cevModuleONS15540Type 167 }

-- ONS 15540 ESPx - 4 Channel Mux/Demux, Band A with OSC

cevONS15540ESPxMDX4ChBOSC  OBJECT IDENTIFIER
    ::= { cevModuleONS15540Type 168 }

-- ONS 15540 ESPx - 4 Channel Mux/Demux, Band B with OSC

cevONS15540ESPxMDX4ChCOSC  OBJECT IDENTIFIER
    ::= { cevModuleONS15540Type 169 }

-- ONS 15540 ESPx - 4 Channel Mux/Demux, Band C with OSC

cevONS15540ESPxMDX4ChDOSC  OBJECT IDENTIFIER
    ::= { cevModuleONS15540Type 170 }

-- ONS 15540 ESPx - 4 Channel Mux/Demux, Band D with OSC

cevONS15540ESPxMDX4ChEOSC  OBJECT IDENTIFIER
    ::= { cevModuleONS15540Type 171 }

-- ONS 15540 ESPx - 4 Channel Mux/Demux, Band E with OSC

cevONS15540ESPxMDX4ChFOSC  OBJECT IDENTIFIER
    ::= { cevModuleONS15540Type 172 }

-- ONS 15540 ESPx - 4 Channel Mux/Demux, Band F with OSC

cevONS15540ESPxMDX4ChGOSC  OBJECT IDENTIFIER
    ::= { cevModuleONS15540Type 173 }

-- ONS 15540 ESPx - 4 Channel Mux/Demux, Band G with OSC

cevONS15540ESPxMDX4ChHOSC  OBJECT IDENTIFIER
    ::= { cevModuleONS15540Type 174 }

-- ONS 15540 ESPx - 4 Channel Mux/Demux, Band H with OSC

cevONS15540ESPxMDX8ChABOSC  OBJECT IDENTIFIER
    ::= { cevModuleONS15540Type 175 }

-- ONS 15540 ESPx - 8 Channel Mux/Demux, Band AB with OSC

cevONS15540ESPxMDX8ChCDOSC  OBJECT IDENTIFIER
    ::= { cevModuleONS15540Type 176 }

-- ONS 15540 ESPx - 8 Channel Mux/Demux, Band CD with OSC

cevONS15540ESPxMDX8ChEFOSC  OBJECT IDENTIFIER
    ::= { cevModuleONS15540Type 177 }

-- ONS 15540 ESPx - 8 Channel Mux/Demux, Band EF with OSC

cevONS15540ESPxMDX8ChGHOSC  OBJECT IDENTIFIER
    ::= { cevModuleONS15540Type 178 }

-- ONS 15540 ESPx - 8 Channel Mux/Demux, Band GH with OSC

cevONS15540ESPxMDX16ChADOSC  OBJECT IDENTIFIER
    ::= { cevModuleONS15540Type 179 }

-- ONS 15540 ESPx - 16 Channel Mux/Demux, Band AD with OSC

cevONS15540ESPxMDX32ChOSC  OBJECT IDENTIFIER
    ::= { cevModuleONS15540Type 180 }

-- ONS 15540 ESPx - 32 Channel Mux/Demux, with OSC

cevONS15540EspPxPSM  OBJECT IDENTIFIER
    ::= { cevModuleONS15540Type 181 }

-- ONS 15540 Protection Switch Module

cevONS15540ESPxVOA1ITUCh1  OBJECT IDENTIFIER
    ::= { cevModuleONS15540Type 182 }

-- ONS 15540 ESPx - 1 Channel VOADM with ITU Laser Channel 1

cevONS15540ESPxVOA1ITUCh2  OBJECT IDENTIFIER
    ::= { cevModuleONS15540Type 183 }

-- ONS 15540 ESPx - 1 Channel VOADM with ITU Laser Channel 2

cevONS15540ESPxVOA1ITUCh3  OBJECT IDENTIFIER
    ::= { cevModuleONS15540Type 184 }

-- ONS 15540 ESPx - 1 Channel VOADM with ITU Laser Channel 3

cevONS15540ESPxVOA1ITUCh4  OBJECT IDENTIFIER
    ::= { cevModuleONS15540Type 185 }

-- ONS 15540 ESPx - 1 Channel VOADM with ITU Laser Channel 4

cevONS15540ESPxVOA1ITUCh5  OBJECT IDENTIFIER
    ::= { cevModuleONS15540Type 186 }

-- ONS 15540 ESPx - 1 Channel VOADM with ITU Laser Channel 5

cevONS15540ESPxVOA1ITUCh6  OBJECT IDENTIFIER
    ::= { cevModuleONS15540Type 187 }

-- ONS 15540 ESPx - 1 Channel VOADM with ITU Laser Channel 6

cevONS15540ESPxVOA1ITUCh7  OBJECT IDENTIFIER
    ::= { cevModuleONS15540Type 188 }

-- ONS 15540 ESPx - 1 Channel VOADM with ITU Laser Channel 7

cevONS15540ESPxVOA1ITUCh8  OBJECT IDENTIFIER
    ::= { cevModuleONS15540Type 189 }

-- ONS 15540 ESPx - 1 Channel VOADM with ITU Laser Channel 8

cevONS15540ESPxVOA1ITUCh9  OBJECT IDENTIFIER
    ::= { cevModuleONS15540Type 190 }

-- ONS 15540 ESPx - 1 Channel VOADM with ITU Laser Channel 9

cevONS15540ESPxVOA1ITUCh10  OBJECT IDENTIFIER
    ::= { cevModuleONS15540Type 191 }

-- ONS 15540 ESPx - 1 Channel VOADM with ITU Laser Channel 10

cevONS15540ESPxVOA1ITUCh11  OBJECT IDENTIFIER
    ::= { cevModuleONS15540Type 192 }

-- ONS 15540 ESPx - 1 Channel VOADM with ITU Laser Channel 11

cevONS15540ESPxVOA1ITUCh12  OBJECT IDENTIFIER
    ::= { cevModuleONS15540Type 193 }

-- ONS 15540 ESPx - 1 Channel VOADM with ITU Laser Channel 12

cevONS15540ESPxVOA1ITUCh13  OBJECT IDENTIFIER
    ::= { cevModuleONS15540Type 194 }

-- ONS 15540 ESPx - 1 Channel VOADM with ITU Laser Channel 13

cevONS15540ESPxVOA1ITUCh14  OBJECT IDENTIFIER
    ::= { cevModuleONS15540Type 195 }

-- ONS 15540 ESPx - 1 Channel VOADM with ITU Laser Channel 14

cevONS15540ESPxVOA1ITUCh15  OBJECT IDENTIFIER
    ::= { cevModuleONS15540Type 196 }

-- ONS 15540 ESPx - 1 Channel VOADM with ITU Laser Channel 15

cevONS15540ESPxVOA1ITUCh16  OBJECT IDENTIFIER
    ::= { cevModuleONS15540Type 197 }

-- ONS 15540 ESPx - 1 Channel VOADM with ITU Laser 16

cevONS15540ESPxVOA1ITUCh17  OBJECT IDENTIFIER
    ::= { cevModuleONS15540Type 198 }

-- ONS 15540 ESPx - 1 Channel VOADM with ITU Laser 17

cevONS15540ESPxVOA1ITUCh18  OBJECT IDENTIFIER
    ::= { cevModuleONS15540Type 199 }

-- ONS 15540 ESPx - 1 Channel VOADM with ITU Laser Channel 18

cevONS15540ESPxVOA1ITUCh19  OBJECT IDENTIFIER
    ::= { cevModuleONS15540Type 200 }

-- ONS 15540 ESPx - 1 Channel VOADM with ITU Laser Channel 19

cevONS15540ESPxVOA1ITUCh20  OBJECT IDENTIFIER
    ::= { cevModuleONS15540Type 201 }

-- ONS 15540 ESPx - 1 Channel VOADM with ITU Laser Channel 20

cevONS15540ESPxVOA1ITUCh21  OBJECT IDENTIFIER
    ::= { cevModuleONS15540Type 202 }

-- ONS 15540 ESPx - 1 Channel VOADM with ITU Laser Channel 21

cevONS15540ESPxVOA1ITUCh22  OBJECT IDENTIFIER
    ::= { cevModuleONS15540Type 203 }

-- ONS 15540 ESPx - 1 Channel VOADM with ITU Laser Channel 22

cevONS15540ESPxVOA1ITUCh23  OBJECT IDENTIFIER
    ::= { cevModuleONS15540Type 204 }

-- ONS 15540 ESPx - 1 Channel VOADM with ITU Laser Channel 23

cevONS15540ESPxVOA1ITUCh24  OBJECT IDENTIFIER
    ::= { cevModuleONS15540Type 205 }

-- ONS 15540 ESPx - 1 Channel VOADM with ITU Laser Channel 24

cevONS15540ESPxVOA1ITUCh25  OBJECT IDENTIFIER
    ::= { cevModuleONS15540Type 206 }

-- ONS 15540 ESPx - 1 Channel VOADM with ITU Laser Channel 25

cevONS15540ESPxVOA1ITUCh26  OBJECT IDENTIFIER
    ::= { cevModuleONS15540Type 207 }

-- ONS 15540 ESPx - 1 Channel VOADM with ITU Laser Channel 26

cevONS15540ESPxVOA1ITUCh27  OBJECT IDENTIFIER
    ::= { cevModuleONS15540Type 208 }

-- ONS 15540 ESPx - 1 Channel VOADM with ITU Laser Channel 27

cevONS15540ESPxVOA1ITUCh28  OBJECT IDENTIFIER
    ::= { cevModuleONS15540Type 209 }

-- ONS 15540 ESPx - 1 Channel VOADM with ITU Laser Channel 28

cevONS15540ESPxVOA1ITUCh29  OBJECT IDENTIFIER
    ::= { cevModuleONS15540Type 210 }

-- ONS 15540 ESPx - 1 Channel VOADM with ITU Laser Channel 29

cevONS15540ESPxVOA1ITUCh30  OBJECT IDENTIFIER
    ::= { cevModuleONS15540Type 211 }

-- ONS 15540 ESPx - 1 Channel VOADM with ITU Laser Channel 30

cevONS15540ESPxVOA1ITUCh31  OBJECT IDENTIFIER
    ::= { cevModuleONS15540Type 212 }

-- ONS 15540 ESPx - 1 Channel VOADM with ITU Laser Channel 31

cevONS15540ESPxVOA1ITUCh32  OBJECT IDENTIFIER
    ::= { cevModuleONS15540Type 213 }

-- ONS 15540 ESPx - 1 Channel VOADM with ITU Laser Channel 32

cevONS15540ESPxVOA1ITUCh33  OBJECT IDENTIFIER
    ::= { cevModuleONS15540Type 214 }

-- ONS 15540 ESPx - 1 Channel VOADM with ITU Laser Channel 33

cevONS15540ESPxVOA2ITUCh0102  OBJECT IDENTIFIER
    ::= { cevModuleONS15540Type 215 }

-- ONS 15540 ESPx - 2 Channel VOADM with ITU Laser Channel 1/2

cevONS15540ESPxVOA2ITUCh0304  OBJECT IDENTIFIER
    ::= { cevModuleONS15540Type 216 }

-- ONS 15540 ESPx - 2 Channel VOADM with ITU Laser Channel 3/4

cevONS15540ESPxVOA2ITUCh0506  OBJECT IDENTIFIER
    ::= { cevModuleONS15540Type 217 }

-- ONS 15540 ESPx - 2 Channel VOADM with ITU Laser Channel 5/6

cevONS15540ESPxVOA2ITUCh0708  OBJECT IDENTIFIER
    ::= { cevModuleONS15540Type 218 }

-- ONS 15540 ESPx - 2 Channel VOADM with ITU Laser Channel 7/8

cevONS15540ESPxVOA2ITUCh0910  OBJECT IDENTIFIER
    ::= { cevModuleONS15540Type 219 }

-- ONS 15540 ESPx - 2 Channel VOADM with ITU Laser Channel 9/10

cevONS15540ESPxVOA2ITUCh1112  OBJECT IDENTIFIER
    ::= { cevModuleONS15540Type 220 }

-- ONS 15540 ESPx - 2 Channel VOADM with ITU Laser Channel 11/12

cevONS15540ESPxVOA2ITUCh1314  OBJECT IDENTIFIER
    ::= { cevModuleONS15540Type 221 }

-- ONS 15540 ESPx - 2 Channel VOADM with ITU Laser Channel 13/14

cevONS15540ESPxVOA2ITUCh1516  OBJECT IDENTIFIER
    ::= { cevModuleONS15540Type 222 }

-- ONS 15540 ESPx - 2 Channel VOADM with ITU Laser Channel 15/16

cevONS15540ESPxVOA2ITUCh1718  OBJECT IDENTIFIER
    ::= { cevModuleONS15540Type 223 }

-- ONS 15540 ESPx - 2 Channel VOADM with ITU Laser Channel 17/18

cevONS15540ESPxVOA2ITUCh1920  OBJECT IDENTIFIER
    ::= { cevModuleONS15540Type 224 }

-- ONS 15540 ESPx - 2 Channel VOADM with ITU Laser Channel 19/20

cevONS15540ESPxVOA2ITUCh2122  OBJECT IDENTIFIER
    ::= { cevModuleONS15540Type 225 }

-- ONS 15540 ESPx - 2 Channel VOADM with ITU Laser Channel 21/22

cevONS15540ESPxVOA2ITUCh2324  OBJECT IDENTIFIER
    ::= { cevModuleONS15540Type 226 }

-- ONS 15540 ESPx - 2 Channel VOADM with ITU Laser Channel 23/24

cevONS15540ESPxVOA2ITUCh2526  OBJECT IDENTIFIER
    ::= { cevModuleONS15540Type 227 }

-- ONS 15540 ESPx - 2 Channel VOADM with ITU Laser Channel 25/26

cevONS15540ESPxVOA2ITUCh2728  OBJECT IDENTIFIER
    ::= { cevModuleONS15540Type 228 }

-- ONS 15540 ESPx - 2 Channel VOADM with ITU Laser Channel 27/28

cevONS15540ESPxVOA2ITUCh2930  OBJECT IDENTIFIER
    ::= { cevModuleONS15540Type 229 }

-- ONS 15540 ESPx - 2 Channel VOADM with ITU Laser Channel 29/30

cevONS15540ESPxVOA2ITUCh3132  OBJECT IDENTIFIER
    ::= { cevModuleONS15540Type 230 }

-- ONS 15540 ESPx - 2 Channel VOADM with ITU Laser Channel 31/32

cevONS15540ESPxVOA4  OBJECT IDENTIFIER
    ::= { cevModuleONS15540Type 231 }

-- ONS 15540 ESPx - 4 Channel VOA

cevModuleGsrPortAdapterType  OBJECT IDENTIFIER
    ::= { cevModule 43 }

-- Port Adapters for GSR

cevGsrPaUnknown  OBJECT IDENTIFIER
    ::= { cevModuleGsrPortAdapterType 1 }

cevGsrPa1Ge  OBJECT IDENTIFIER
    ::= { cevModuleGsrPortAdapterType 2 }

-- 1 Port Gigabit Ethernet Port Adapter Of Modular Gigabit/Fast Ethernet card for GSR

cevGsrPa3Ge  OBJECT IDENTIFIER
    ::= { cevModuleGsrPortAdapterType 3 }

-- 3 Port Gigabit Ethernet Port Adapter Of Modular Gigabit/Fast Ethernet card for GSR

cevGsrPa24Fe  OBJECT IDENTIFIER
    ::= { cevModuleGsrPortAdapterType 4 }

-- 24 Port Fast Ethernet Port Adapter Of Modular Gigabit/Fast Ethernet card for GSR

cevModuleC4224Type  OBJECT IDENTIFIER
    ::= { cevModule 47 }

-- Cisco Access Gateway Switch platform

cevC42241FeTx  OBJECT IDENTIFIER
    ::= { cevModuleC4224Type 1 }

-- Onboard 1 FastEthernet management port for c4224 platform

cevC422424FeTx  OBJECT IDENTIFIER
    ::= { cevModuleC4224Type 2 }

-- Onboard 24 10/100 FastEthernet ports for c4224 platform

cevModuleONS15530Type  OBJECT IDENTIFIER
    ::= { cevModule 44 }

-- Cisco ONS 15530 Modules

cevONS15530LCMBOsc  OBJECT IDENTIFIER
    ::= { cevModuleONS15530Type 1 }

-- ONS 15530 Optical Supervisor Channel Line Card Motherboard

cevONS15530Osc  OBJECT IDENTIFIER
    ::= { cevModuleONS15530Type 2 }

-- ONS 15530 Optical Supervisor Channel Module

cevONS15530MDX4ChA  OBJECT IDENTIFIER
    ::= { cevModuleONS15530Type 3 }

-- ONS 15530 4-Channel Band A Mux/Demux Module - without OSC

cevONS15530MDX4ChB  OBJECT IDENTIFIER
    ::= { cevModuleONS15530Type 4 }

-- ONS 15530 4-Channel Band B Mux/Demux Module - without OSC

cevONS15530MDX4ChC  OBJECT IDENTIFIER
    ::= { cevModuleONS15530Type 5 }

-- ONS 15530 4-Channel Band C Mux/Demux Module - without OSC

cevONS15530MDX4ChD  OBJECT IDENTIFIER
    ::= { cevModuleONS15530Type 6 }

-- ONS 15530 4-Channel Band D Mux/Demux Module - without OSC

cevONS15530MDX4ChE  OBJECT IDENTIFIER
    ::= { cevModuleONS15530Type 7 }

-- ONS 15530 4-Channel Band E Mux/Demux Module - without OSC

cevONS15530MDX4ChF  OBJECT IDENTIFIER
    ::= { cevModuleONS15530Type 8 }

-- ONS 15530 4-Channel Band F Mux/Demux Module - without OSC

cevONS15530MDX4ChG  OBJECT IDENTIFIER
    ::= { cevModuleONS15530Type 9 }

-- ONS 15530 4-Channel Band G Mux/Demux Module - without OSC

cevONS15530MDX4ChH  OBJECT IDENTIFIER
    ::= { cevModuleONS15530Type 10 }

-- ONS 15530 4-Channel Band H Mux/Demux Module - without OSC

cevONS15530MDX4ChAOsc  OBJECT IDENTIFIER
    ::= { cevModuleONS15530Type 11 }

-- ONS 15530 4-Channel Band A Mux/Demux Module - with OSC

cevONS15530MDX4ChBOsc  OBJECT IDENTIFIER
    ::= { cevModuleONS15530Type 12 }

-- ONS 15530 4-Channel Band B Mux/Demux Module - with OSC

cevONS15530MDX4ChCOsc  OBJECT IDENTIFIER
    ::= { cevModuleONS15530Type 13 }

-- ONS 15530 4-Channel Band C Mux/Demux Module - with OSC

cevONS15530MDX4ChDOsc  OBJECT IDENTIFIER
    ::= { cevModuleONS15530Type 14 }

-- ONS 15530 4-Channel Band D Mux/Demux Module - with OSC

cevONS15530MDX4ChEOsc  OBJECT IDENTIFIER
    ::= { cevModuleONS15530Type 15 }

-- ONS 15530 4-Channel Band E Mux/Demux Module - with OSC

cevONS15530MDX4ChFOsc  OBJECT IDENTIFIER
    ::= { cevModuleONS15530Type 16 }

-- ONS 15530 4-Channel Band F Mux/Demux Module - with OSC

cevONS15530MDX4ChGOsc  OBJECT IDENTIFIER
    ::= { cevModuleONS15530Type 17 }

-- ONS 15530 4-Channel Band G Mux/Demux Module - with OSC

cevONS15530MDX4ChHOsc  OBJECT IDENTIFIER
    ::= { cevModuleONS15530Type 18 }

-- ONS 15530 4-Channel Band H Mux/Demux Module - with OSC

cevONS15530Tsp1Ch0102MmScSp  OBJECT IDENTIFIER
    ::= { cevModuleONS15530Type 19 }

-- Transponder Type I linecard, channel 1 or 2,  1310-nm MM, SC connector, with splitter

cevONS15530Tsp1Ch0304MmScSp  OBJECT IDENTIFIER
    ::= { cevModuleONS15530Type 20 }

-- Transponder Type I linecard, channel 3 or 4, 1310-nm MM, SC connector, with splitter

cevONS15530Tsp1Ch0506MmScSp  OBJECT IDENTIFIER
    ::= { cevModuleONS15530Type 21 }

-- Transponder Type I linecard, channel 5 or 6, 1310-nm MM, SC connector, with splitter

cevONS15530Tsp1Ch0708MmScSp  OBJECT IDENTIFIER
    ::= { cevModuleONS15530Type 22 }

-- Transponder Type I linecard, channel 7 or 8, 1310-nm MM, SC connector, with splitter

cevONS15530Tsp1Ch0910MmScSp  OBJECT IDENTIFIER
    ::= { cevModuleONS15530Type 23 }

-- Transponder Type I linecard, channel 9 or 10, 1310-nm MM, SC connector, with splitter

cevONS15530Tsp1Ch1112MmScSp  OBJECT IDENTIFIER
    ::= { cevModuleONS15530Type 24 }

-- Transponder Type I linecard, channel 11 or 12, 1310-nm MM, SC connector, with splitter

cevONS15530Tsp1Ch1314MmScSp  OBJECT IDENTIFIER
    ::= { cevModuleONS15530Type 25 }

-- Transponder Type I linecard, channel 13 or 14, 1310-nm MM, SC connector, with splitter

cevONS15530Tsp1Ch1516MmScSp  OBJECT IDENTIFIER
    ::= { cevModuleONS15530Type 26 }

-- Transponder Type I linecard, channel 15 or 16, 1310-nm MM, SC connector, with splitter

cevONS15530Tsp1Ch1718MmScSp  OBJECT IDENTIFIER
    ::= { cevModuleONS15530Type 27 }

-- Transponder Type I linecard, channel 17 or 18, 1310-nm MM, SC connector, with splitter

cevONS15530Tsp1Ch1920MmScSp  OBJECT IDENTIFIER
    ::= { cevModuleONS15530Type 28 }

-- Transponder Type I linecard, channel 19 or 20, 1310-nm MM, SC connector, with splitter

cevONS15530Tsp1Ch2122MmScSp  OBJECT IDENTIFIER
    ::= { cevModuleONS15530Type 29 }

-- Transponder Type I linecard, channel 21 or 22, 1310-nm MM, SC connector, with splitter

cevONS15530Tsp1Ch2324MmScSp  OBJECT IDENTIFIER
    ::= { cevModuleONS15530Type 30 }

-- Transponder Type I linecard, channel 23 or 24, 1310-nm MM, SC connector, with splitter

cevONS15530Tsp1Ch2526MmScSp  OBJECT IDENTIFIER
    ::= { cevModuleONS15530Type 31 }

-- Transponder Type I linecard, channel 25 or 26, 1310-nm MM, SC connector, with splitter

cevONS15530Tsp1Ch2728MmScSp  OBJECT IDENTIFIER
    ::= { cevModuleONS15530Type 32 }

-- Transponder Type I linecard, channel 27 or 28, 1310-nm MM, SC connector, with splitter

cevONS15530Tsp1Ch2930MmScSp  OBJECT IDENTIFIER
    ::= { cevModuleONS15530Type 33 }

-- Transponder Type I linecard, channel 29 or 30, 1310-nm MM, SC connector, with splitter

cevONS15530Tsp1Ch3132MmScSp  OBJECT IDENTIFIER
    ::= { cevModuleONS15530Type 34 }

-- Transponder Type I linecard, channel 31 or 32, 1310-nm MM, SC connector, with splitter

cevONS15530Tsp1Ch0102SmScSp  OBJECT IDENTIFIER
    ::= { cevModuleONS15530Type 35 }

-- Transponder Type I linecard, channel 1 or 2,  1310-nm SM, SC connector, with splitter

cevONS15530Tsp1Ch0304SmScSp  OBJECT IDENTIFIER
    ::= { cevModuleONS15530Type 36 }

-- Transponder Type I linecard, channel 3 or 4, 1310-nm SM, SC connector, with splitter

cevONS15530Tsp1Ch0506SmScSp  OBJECT IDENTIFIER
    ::= { cevModuleONS15530Type 37 }

-- Transponder Type I linecard, channel 5 or 6, 1310-nm SM, SC connector, with splitter

cevONS15530Tsp1Ch0708SmScSp  OBJECT IDENTIFIER
    ::= { cevModuleONS15530Type 38 }

-- Transponder Type I linecard, channel 7 or 8, 1310-nm SM, SC connector, with splitter

cevONS15530Tsp1Ch0910SmScSp  OBJECT IDENTIFIER
    ::= { cevModuleONS15530Type 39 }

-- Transponder Type I linecard, channel 9 or 10, 1310-nm SM, SC connector, with splitter

cevONS15530Tsp1Ch1112SmScSp  OBJECT IDENTIFIER
    ::= { cevModuleONS15530Type 40 }

-- Transponder Type I linecard, channel 11 or 12, 1310-nm SM, SC connector, with splitter

cevONS15530Tsp1Ch1314SmScSp  OBJECT IDENTIFIER
    ::= { cevModuleONS15530Type 41 }

-- Transponder Type I linecard, channel 13 or 14, 1310-nm SM, SC connector, with splitter

cevONS15530Tsp1Ch1516SmScSp  OBJECT IDENTIFIER
    ::= { cevModuleONS15530Type 42 }

-- Transponder Type I linecard, channel 15 or 16, 1310-nm SM, SC connector, with splitter

cevONS15530Tsp1Ch1718SmScSp  OBJECT IDENTIFIER
    ::= { cevModuleONS15530Type 43 }

-- Transponder Type I linecard, channel 17 or 18, 1310-nm SM, SC connector, with splitter

cevONS15530Tsp1Ch1920SmScSp  OBJECT IDENTIFIER
    ::= { cevModuleONS15530Type 44 }

-- Transponder Type I linecard, channel 19 or 20, 1310-nm SM, SC connector, with splitter

cevONS15530Tsp1Ch2122SmScSp  OBJECT IDENTIFIER
    ::= { cevModuleONS15530Type 45 }

-- Transponder Type I linecard, channel 21 or 22, 1310-nm SM, SC connector, with splitter

cevONS15530Tsp1Ch2324SmScSp  OBJECT IDENTIFIER
    ::= { cevModuleONS15530Type 46 }

-- Transponder Type I linecard, channel 23 or 24, 1310-nm SM, SC connector, with splitter

cevONS15530Tsp1Ch2526SmScSp  OBJECT IDENTIFIER
    ::= { cevModuleONS15530Type 47 }

-- Transponder Type I linecard, channel 25 or 26, 1310-nm SM, SC connector, with splitter

cevONS15530Tsp1Ch2728SmScSp  OBJECT IDENTIFIER
    ::= { cevModuleONS15530Type 48 }

-- Transponder Type I linecard, channel 27 or 28, 1310-nm SM, SC connector, with splitter

cevONS15530Tsp1Ch2930SmScSp  OBJECT IDENTIFIER
    ::= { cevModuleONS15530Type 49 }

-- Transponder Type I linecard, channel 29 or 30, 1310-nm SM, SC connector, with splitter

cevONS15530Tsp1Ch3132SmScSp  OBJECT IDENTIFIER
    ::= { cevModuleONS15530Type 50 }

-- Transponder Type I linecard, channel 31 or 32, 1310-nm SM, SC connector, with splitter

cevONS15530Tsp1Ch0102MmSc  OBJECT IDENTIFIER
    ::= { cevModuleONS15530Type 51 }

-- Transponder Type I linecard, channel 1 or 2,  1310-nm MM, SC connector, without splitter

cevONS15530Tsp1Ch0304MmSc  OBJECT IDENTIFIER
    ::= { cevModuleONS15530Type 52 }

-- Transponder Type I linecard, channel 3 or 4, 1310-nm MM, SC connector, without splitter

cevONS15530Tsp1Ch0506MmSc  OBJECT IDENTIFIER
    ::= { cevModuleONS15530Type 53 }

-- Transponder Type I linecard, channel 5 or 6, 1310-nm MM, SC connector, without splitter

cevONS15530Tsp1Ch0708MmSc  OBJECT IDENTIFIER
    ::= { cevModuleONS15530Type 54 }

-- Transponder Type I linecard, channel 7 or 8, 1310-nm MM, SC connector, without splitter

cevONS15530Tsp1Ch0910MmSc  OBJECT IDENTIFIER
    ::= { cevModuleONS15530Type 55 }

-- Transponder Type I linecard, channel 9 or 10, 1310-nm MM, SC connector, without splitter

cevONS15530Tsp1Ch1112MmSc  OBJECT IDENTIFIER
    ::= { cevModuleONS15530Type 56 }

-- Transponder Type I linecard, channel 11 or 12, 1310-nm MM, SC connector, without splitter

cevONS15530Tsp1Ch1314MmSc  OBJECT IDENTIFIER
    ::= { cevModuleONS15530Type 57 }

-- Transponder Type I linecard, channel 13 or 14, 1310-nm MM, SC connector, without splitter

cevONS15530Tsp1Ch1516MmSc  OBJECT IDENTIFIER
    ::= { cevModuleONS15530Type 58 }

-- Transponder Type I linecard, channel 15 or 16, 1310-nm MM, SC connector, without splitter

cevONS15530Tsp1Ch1718MmSc  OBJECT IDENTIFIER
    ::= { cevModuleONS15530Type 59 }

-- Transponder Type I linecard, channel 17 or 18, 1310-nm MM, SC connector, without splitter

cevONS15530Tsp1Ch1920MmSc  OBJECT IDENTIFIER
    ::= { cevModuleONS15530Type 60 }

-- Transponder Type I linecard, channel 19 or 20, 1310-nm MM, SC connector, without splitter

cevONS15530Tsp1Ch2122MmSc  OBJECT IDENTIFIER
    ::= { cevModuleONS15530Type 61 }

-- Transponder Type I linecard, channel 21 or 22, 1310-nm MM, SC connector, without splitter

cevONS15530Tsp1Ch2324MmSc  OBJECT IDENTIFIER
    ::= { cevModuleONS15530Type 62 }

-- Transponder Type I linecard, channel 23 or 24, 1310-nm MM, SC connector, without splitter

cevONS15530Tsp1Ch2526MmSc  OBJECT IDENTIFIER
    ::= { cevModuleONS15530Type 63 }

-- Transponder Type I linecard, channel 25 or 26, 1310-nm MM, SC connector, without splitter

cevONS15530Tsp1Ch2728MmSc  OBJECT IDENTIFIER
    ::= { cevModuleONS15530Type 64 }

-- Transponder Type I linecard, channel 27 or 28, 1310-nm MM, SC connector, without splitter

cevONS15530Tsp1Ch2930MmSc  OBJECT IDENTIFIER
    ::= { cevModuleONS15530Type 65 }

-- Transponder Type I linecard, channel 29 or 30, 1310-nm MM, SC connector, without splitter

cevONS15530Tsp1Ch3132MmSc  OBJECT IDENTIFIER
    ::= { cevModuleONS15530Type 66 }

-- Transponder Type I linecard, channel 31 or 32, 1310-nm MM, SC connector, without splitter

cevONS15530Tsp1Ch0102SmSc  OBJECT IDENTIFIER
    ::= { cevModuleONS15530Type 67 }

-- Transponder Type I linecard, channel 1 or 2,  1310-nm SM, SC connector, without splitter

cevONS15530Tsp1Ch0304SmSc  OBJECT IDENTIFIER
    ::= { cevModuleONS15530Type 68 }

-- Transponder Type I linecard, channel 3 or 4, 1310-nm SM, SC connector, without splitter

cevONS15530Tsp1Ch0506SmSc  OBJECT IDENTIFIER
    ::= { cevModuleONS15530Type 69 }

-- Transponder Type I linecard, channel 5 or 6, 1310-nm SM, SC connector, without splitter

cevONS15530Tsp1Ch0708SmSc  OBJECT IDENTIFIER
    ::= { cevModuleONS15530Type 70 }

-- Transponder Type I linecard, channel 7 or 8, 1310-nm SM, SC connector, without splitter

cevONS15530Tsp1Ch0910SmSc  OBJECT IDENTIFIER
    ::= { cevModuleONS15530Type 71 }

-- Transponder Type I linecard, channel 9 or 10, 1310-nm SM, SC connector, without splitter

cevONS15530Tsp1Ch1112SmSc  OBJECT IDENTIFIER
    ::= { cevModuleONS15530Type 72 }

-- Transponder Type I linecard, channel 11 or 12, 1310-nm SM, SC connector, without splitter

cevONS15530Tsp1Ch1314SmSc  OBJECT IDENTIFIER
    ::= { cevModuleONS15530Type 73 }

-- Transponder Type I linecard, channel 13 or 14, 1310-nm SM, SC connector, without splitter

cevONS15530Tsp1Ch1516SmSc  OBJECT IDENTIFIER
    ::= { cevModuleONS15530Type 74 }

-- Transponder Type I linecard, channel 15 or 16, 1310-nm SM, SC connector, without splitter

cevONS15530Tsp1Ch1718SmSc  OBJECT IDENTIFIER
    ::= { cevModuleONS15530Type 75 }

-- Transponder Type I linecard, channel 17 or 18, 1310-nm SM, SC connector, without splitter

cevONS15530Tsp1Ch1920SmSc  OBJECT IDENTIFIER
    ::= { cevModuleONS15530Type 76 }

-- Transponder Type I linecard, channel 19 or 20, 1310-nm SM, SC connector, without splitter

cevONS15530Tsp1Ch2122SmSc  OBJECT IDENTIFIER
    ::= { cevModuleONS15530Type 77 }

-- Transponder Type I linecard, channel 21 or 22, 1310-nm SM, SC connector, without splitter

cevONS15530Tsp1Ch2324SmSc  OBJECT IDENTIFIER
    ::= { cevModuleONS15530Type 78 }

-- Transponder Type I linecard, channel 23 or 24, 1310-nm SM, SC connector, without splitter

cevONS15530Tsp1Ch2526SmSc  OBJECT IDENTIFIER
    ::= { cevModuleONS15530Type 79 }

-- Transponder Type I linecard, channel 25 or 26, 1310-nm SM, SC connector, without splitter

cevONS15530Tsp1Ch2728SmSc  OBJECT IDENTIFIER
    ::= { cevModuleONS15530Type 80 }

-- Transponder Type I linecard, channel 27 or 28, 1310-nm SM, SC connector, without splitter

cevONS15530Tsp1Ch2930SmSc  OBJECT IDENTIFIER
    ::= { cevModuleONS15530Type 81 }

-- Transponder Type I linecard, channel 29 or 30, 1310-nm SM, SC connector, without splitter

cevONS15530Tsp1Ch3132SmSc  OBJECT IDENTIFIER
    ::= { cevModuleONS15530Type 82 }

-- Transponder Type I linecard, channel 31 or 32, 1310-nm SM, SC connector, without splitter

cevONS15530LCEscon10  OBJECT IDENTIFIER
    ::= { cevModuleONS15530Type 83 }

-- ONS 15530 10-port ESCON Multiplexing Line Card

cevONS15500XvrEscon1310MmMTRJ  OBJECT IDENTIFIER
    ::= { cevModuleONS15530Type 84 }

-- ONS 15500 Pluggable Transceiver Escon - 1310nm MM - MTRJ

cevONS15530LC10GESmSc  OBJECT IDENTIFIER
    ::= { cevModuleONS15530Type 85 }

-- ONS 15530 10Gbps Uplink, 1310nm with SC

cevONS1553010GCh01Sp  OBJECT IDENTIFIER
    ::= { cevModuleONS15530Type 86 }

-- ONS 15530 Ch 01 10Gbps ITU Line Card MU with Splitter

cevONS1553010GCh02Sp  OBJECT IDENTIFIER
    ::= { cevModuleONS15530Type 87 }

-- ONS 15530 Ch 02 10Gbps ITU Line Card MU with Splitter

cevONS1553010GCh03Sp  OBJECT IDENTIFIER
    ::= { cevModuleONS15530Type 88 }

-- ONS 15530 Ch 03 10Gbps ITU Line Card MU with Splitter

cevONS1553010GCh04Sp  OBJECT IDENTIFIER
    ::= { cevModuleONS15530Type 89 }

-- ONS 15530 Ch 04 10Gbps ITU Line Card MU with Splitter

cevONS1553010GCh05Sp  OBJECT IDENTIFIER
    ::= { cevModuleONS15530Type 90 }

-- ONS 15530 Ch 05 10Gbps ITU Line Card MU with Splitter

cevONS1553010GCh06Sp  OBJECT IDENTIFIER
    ::= { cevModuleONS15530Type 91 }

-- ONS 15530 Ch 06 10Gbps ITU Line Card MU with Splitter

cevONS1553010GCh07Sp  OBJECT IDENTIFIER
    ::= { cevModuleONS15530Type 92 }

-- ONS 15530 Ch 07 10Gbps ITU Line Card MU with Splitter

cevONS1553010GCh08Sp  OBJECT IDENTIFIER
    ::= { cevModuleONS15530Type 93 }

-- ONS 15530 Ch 08 10Gbps ITU Line Card MU with Splitter

cevONS1553010GCh09Sp  OBJECT IDENTIFIER
    ::= { cevModuleONS15530Type 94 }

-- ONS 15530 Ch 09 10Gbps ITU Line Card MU with Splitter

cevONS1553010GCh10Sp  OBJECT IDENTIFIER
    ::= { cevModuleONS15530Type 95 }

-- ONS 15530 Ch 10 10Gbps ITU Line Card MU with Splitter

cevONS1553010GCh11Sp  OBJECT IDENTIFIER
    ::= { cevModuleONS15530Type 96 }

-- ONS 15530 Ch 11 10Gbps ITU Line Card MU with Splitter

cevONS1553010GCh12Sp  OBJECT IDENTIFIER
    ::= { cevModuleONS15530Type 97 }

-- ONS 15530 Ch 12 10Gbps ITU Line Card MU with Splitter

cevONS1553010GCh13Sp  OBJECT IDENTIFIER
    ::= { cevModuleONS15530Type 98 }

-- ONS 15530 Ch 13 10Gbps ITU Line Card MU with Splitter

cevONS1553010GCh14Sp  OBJECT IDENTIFIER
    ::= { cevModuleONS15530Type 99 }

-- ONS 15530 Ch 14 10Gbps ITU Line Card MU with Splitter

cevONS1553010GCh15Sp  OBJECT IDENTIFIER
    ::= { cevModuleONS15530Type 100 }

-- ONS 15530 Ch 15 10Gbps ITU Line Card MU with Splitter

cevONS1553010GCh16Sp  OBJECT IDENTIFIER
    ::= { cevModuleONS15530Type 101 }

-- ONS 15530 Ch 16 10Gbps ITU Line Card MU with Splitter

cevONS1553010GCh17Sp  OBJECT IDENTIFIER
    ::= { cevModuleONS15530Type 102 }

-- ONS 15530 Ch 17 10Gbps ITU Line Card MU with Splitter

cevONS1553010GCh18Sp  OBJECT IDENTIFIER
    ::= { cevModuleONS15530Type 103 }

-- ONS 15530 Ch 18 10Gbps ITU Line Card MU with Splitter

cevONS1553010GCh19Sp  OBJECT IDENTIFIER
    ::= { cevModuleONS15530Type 104 }

-- ONS 15530 Ch 19 10Gbps ITU Line Card MU with Splitter

cevONS1553010GCh20Sp  OBJECT IDENTIFIER
    ::= { cevModuleONS15530Type 105 }

-- ONS 15530 Ch 20 10Gbps ITU Line Card MU with Splitter

cevONS1553010GCh21Sp  OBJECT IDENTIFIER
    ::= { cevModuleONS15530Type 106 }

-- ONS 15530 Ch 21 10Gbps ITU Line Card MU with Splitter

cevONS1553010GCh22Sp  OBJECT IDENTIFIER
    ::= { cevModuleONS15530Type 107 }

-- ONS 15530 Ch 22 10Gbps ITU Line Card MU with Splitter

cevONS1553010GCh23Sp  OBJECT IDENTIFIER
    ::= { cevModuleONS15530Type 108 }

-- ONS 15530 Ch 23 10Gbps ITU Line Card MU with Splitter

cevONS1553010GCh24Sp  OBJECT IDENTIFIER
    ::= { cevModuleONS15530Type 109 }

-- ONS 15530 Ch 24 10Gbps ITU Line Card MU with Splitter

cevONS1553010GCh25Sp  OBJECT IDENTIFIER
    ::= { cevModuleONS15530Type 110 }

-- ONS 15530 Ch 25 10Gbps ITU Line Card MU with Splitter

cevONS1553010GCh26Sp  OBJECT IDENTIFIER
    ::= { cevModuleONS15530Type 111 }

-- ONS 15530 Ch 26 10Gbps ITU Line Card MU with Splitter

cevONS1553010GCh27Sp  OBJECT IDENTIFIER
    ::= { cevModuleONS15530Type 112 }

-- ONS 15530 Ch 27 10Gbps ITU Line Card MU with Splitter

cevONS1553010GCh28Sp  OBJECT IDENTIFIER
    ::= { cevModuleONS15530Type 113 }

-- ONS 15530 Ch 28 10Gbps ITU Line Card MU with Splitter

cevONS1553010GCh29Sp  OBJECT IDENTIFIER
    ::= { cevModuleONS15530Type 114 }

-- ONS 15530 Ch 29 10Gbps ITU Line Card MU with Splitter

cevONS1553010GCh30Sp  OBJECT IDENTIFIER
    ::= { cevModuleONS15530Type 115 }

-- ONS 15530 Ch 30 10Gbps ITU Line Card MU with Splitter

cevONS1553010GCh31Sp  OBJECT IDENTIFIER
    ::= { cevModuleONS15530Type 116 }

-- ONS 15530 Ch 31 10Gbps ITU Line Card MU with Splitter

cevONS1553010GCh32Sp  OBJECT IDENTIFIER
    ::= { cevModuleONS15530Type 117 }

-- ONS 15530 Ch 32 10Gbps ITU Line Card MU with Splitter

cevONS1553010GCh01  OBJECT IDENTIFIER
    ::= { cevModuleONS15530Type 118 }

-- ONS 15530 Ch 01 10Gbps ITU Line Card MU without Splitter

cevONS1553010GCh02  OBJECT IDENTIFIER
    ::= { cevModuleONS15530Type 119 }

-- ONS 15530 Ch 02 10Gbps ITU Line Card MU without Splitter

cevONS1553010GCh03  OBJECT IDENTIFIER
    ::= { cevModuleONS15530Type 120 }

-- ONS 15530 Ch 03 10Gbps ITU Line Card MU without Splitter

cevONS1553010GCh04  OBJECT IDENTIFIER
    ::= { cevModuleONS15530Type 121 }

-- ONS 15530 Ch 04 10Gbps ITU Line Card MU without Splitter

cevONS1553010GCh05  OBJECT IDENTIFIER
    ::= { cevModuleONS15530Type 122 }

-- ONS 15530 Ch 05 10Gbps ITU Line Card MU without Splitter

cevONS1553010GCh06  OBJECT IDENTIFIER
    ::= { cevModuleONS15530Type 123 }

-- ONS 15530 Ch 06 10Gbps ITU Line Card MU without Splitter

cevONS1553010GCh07  OBJECT IDENTIFIER
    ::= { cevModuleONS15530Type 124 }

-- ONS 15530 Ch 07 10Gbps ITU Line Card MU without Splitter

cevONS1553010GCh08  OBJECT IDENTIFIER
    ::= { cevModuleONS15530Type 125 }

-- ONS 15530 Ch 08 10Gbps ITU Line Card MU without Splitter

cevONS1553010GCh09  OBJECT IDENTIFIER
    ::= { cevModuleONS15530Type 126 }

-- ONS 15530 Ch 09 10Gbps ITU Line Card MU without Splitter

cevONS1553010GCh10  OBJECT IDENTIFIER
    ::= { cevModuleONS15530Type 127 }

-- ONS 15530 Ch 10 10Gbps ITU Line Card MU without Splitter

cevONS1553010GCh11  OBJECT IDENTIFIER
    ::= { cevModuleONS15530Type 128 }

-- ONS 15530 Ch 11 10Gbps ITU Line Card MU without Splitter

cevONS1553010GCh12  OBJECT IDENTIFIER
    ::= { cevModuleONS15530Type 129 }

-- ONS 15530 Ch 12 10Gbps ITU Line Card MU without Splitter

cevONS1553010GCh13  OBJECT IDENTIFIER
    ::= { cevModuleONS15530Type 130 }

-- ONS 15530 Ch 13 10Gbps ITU Line Card MU without Splitter

cevONS1553010GCh14  OBJECT IDENTIFIER
    ::= { cevModuleONS15530Type 131 }

-- ONS 15530 Ch 14 10Gbps ITU Line Card MU without Splitter

cevONS1553010GCh15  OBJECT IDENTIFIER
    ::= { cevModuleONS15530Type 132 }

-- ONS 15530 Ch 15 10Gbps ITU Line Card MU without Splitter

cevONS1553010GCh16  OBJECT IDENTIFIER
    ::= { cevModuleONS15530Type 133 }

-- ONS 15530 Ch 16 10Gbps ITU Line Card MU without Splitter

cevONS1553010GCh17  OBJECT IDENTIFIER
    ::= { cevModuleONS15530Type 134 }

-- ONS 15530 Ch 17 10Gbps ITU Line Card MU without Splitter

cevONS1553010GCh18  OBJECT IDENTIFIER
    ::= { cevModuleONS15530Type 135 }

-- ONS 15530 Ch 18 10Gbps ITU Line Card MU without Splitter

cevONS1553010GCh19  OBJECT IDENTIFIER
    ::= { cevModuleONS15530Type 136 }

-- ONS 15530 Ch 19 10Gbps ITU Line Card MU without Splitter

cevONS1553010GCh20  OBJECT IDENTIFIER
    ::= { cevModuleONS15530Type 137 }

-- ONS 15530 Ch 20 10Gbps ITU Line Card MU without Splitter

cevONS1553010GCh21  OBJECT IDENTIFIER
    ::= { cevModuleONS15530Type 138 }

-- ONS 15530 Ch 21 10Gbps ITU Line Card MU without Splitter

cevONS1553010GCh22  OBJECT IDENTIFIER
    ::= { cevModuleONS15530Type 139 }

-- ONS 15530 Ch 22 10Gbps ITU Line Card MU without Splitter

cevONS1553010GCh23  OBJECT IDENTIFIER
    ::= { cevModuleONS15530Type 140 }

-- ONS 15530 Ch 23 10Gbps ITU Line Card MU without Splitter

cevONS1553010GCh24  OBJECT IDENTIFIER
    ::= { cevModuleONS15530Type 141 }

-- ONS 15530 Ch 24 10Gbps ITU Line Card MU without Splitter

cevONS1553010GCh25  OBJECT IDENTIFIER
    ::= { cevModuleONS15530Type 142 }

-- ONS 15530 Ch 25 10Gbps ITU Line Card MU without Splitter

cevONS1553010GCh26  OBJECT IDENTIFIER
    ::= { cevModuleONS15530Type 143 }

-- ONS 15530 Ch 26 10Gbps ITU Line Card MU without Splitter

cevONS1553010GCh27  OBJECT IDENTIFIER
    ::= { cevModuleONS15530Type 144 }

-- ONS 15530 Ch 27 10Gbps ITU Line Card MU without Splitter

cevONS1553010GCh28  OBJECT IDENTIFIER
    ::= { cevModuleONS15530Type 145 }

-- ONS 15530 Ch 28 10Gbps ITU Line Card MU without Splitter

cevONS1553010GCh29  OBJECT IDENTIFIER
    ::= { cevModuleONS15530Type 146 }

-- ONS 15530 Ch 29 10Gbps ITU Line Card MU without Splitter

cevONS1553010GCh30  OBJECT IDENTIFIER
    ::= { cevModuleONS15530Type 147 }

-- ONS 15530 Ch 30 10Gbps ITU Line Card MU without Splitter

cevONS1553010GCh31  OBJECT IDENTIFIER
    ::= { cevModuleONS15530Type 148 }

-- ONS 15530 Ch 31 10Gbps ITU Line Card MU without Splitter

cevONS1553010GCh32  OBJECT IDENTIFIER
    ::= { cevModuleONS15530Type 149 }

-- ONS 15530 Ch 32 10Gbps ITU Line Card MU without Splitter

cevONS15530FCGE8P  OBJECT IDENTIFIER
    ::= { cevModuleONS15530Type 150 }

-- ONS 15530 8-port Fibre Channel/Gigabit Ethernet Linecard

cevONS155302p5GCh0102Sp  OBJECT IDENTIFIER
    ::= { cevModuleONS15530Type 151 }

-- ONS 15530 Channel 01 or 02 2.5 Gbps ITU Line Card MU with Splitter

cevONS155302p5GCh0304Sp  OBJECT IDENTIFIER
    ::= { cevModuleONS15530Type 152 }

-- ONS 15530 Channel 03 or 04 2.5 Gbps ITU Line Card MU with Splitter

cevONS155302p5GCh0506Sp  OBJECT IDENTIFIER
    ::= { cevModuleONS15530Type 153 }

-- ONS 15530 Channel 05 or 06 2.5 Gbps ITU Line Card MU with Splitter

cevONS155302p5GCh0708Sp  OBJECT IDENTIFIER
    ::= { cevModuleONS15530Type 154 }

-- ONS 15530 Channel 07 or 08 2.5 Gbps ITU Line Card MU with Splitter

cevONS155302p5GCh0910Sp  OBJECT IDENTIFIER
    ::= { cevModuleONS15530Type 155 }

-- ONS 15530 Channel 09 or 10 2.5 Gbps ITU Line Card MU with Splitter

cevONS155302p5GCh1112Sp  OBJECT IDENTIFIER
    ::= { cevModuleONS15530Type 156 }

-- ONS 15530 Channel 11 or 12 2.5 Gbps ITU Line Card MU with Splitter

cevONS155302p5GCh1314Sp  OBJECT IDENTIFIER
    ::= { cevModuleONS15530Type 157 }

-- ONS 15530 Channel 13 or 14 2.5 Gbps ITU Line Card MU with Splitter

cevONS155302p5GCh1516Sp  OBJECT IDENTIFIER
    ::= { cevModuleONS15530Type 158 }

-- ONS 15530 Channel 15 or 16 2.5 Gbps ITU Line Card MU with Splitter

cevONS155302p5GCh1718Sp  OBJECT IDENTIFIER
    ::= { cevModuleONS15530Type 159 }

-- ONS 15530 Channel 17 or 18 2.5 Gbps ITU Line Card MU with Splitter

cevONS155302p5GCh1920Sp  OBJECT IDENTIFIER
    ::= { cevModuleONS15530Type 160 }

-- ONS 15530 Channel 19 or 20 2.5 Gbps ITU Line Card MU with Splitter

cevONS155302p5GCh2122Sp  OBJECT IDENTIFIER
    ::= { cevModuleONS15530Type 161 }

-- ONS 15530 Channel 21 or 22 2.5 Gbps ITU Line Card MU with Splitter

cevONS155302p5GCh2324Sp  OBJECT IDENTIFIER
    ::= { cevModuleONS15530Type 162 }

-- ONS 15530 Channel 23 or 24 2.5 Gbps ITU Line Card MU with Splitter

cevONS155302p5GCh2526Sp  OBJECT IDENTIFIER
    ::= { cevModuleONS15530Type 163 }

-- ONS 15530 Channel 25 or 26 2.5 Gbps ITU Line Card MU with Splitter

cevONS155302p5GCh2728Sp  OBJECT IDENTIFIER
    ::= { cevModuleONS15530Type 164 }

-- ONS 15530 Channel 27 or 28 2.5 Gbps ITU Line Card MU with Splitter

cevONS155302p5GCh2930Sp  OBJECT IDENTIFIER
    ::= { cevModuleONS15530Type 165 }

-- ONS 15530 Channel 29 or 30 2.5 Gbps ITU Line Card MU with Splitter

cevONS155302p5GCh3132Sp  OBJECT IDENTIFIER
    ::= { cevModuleONS15530Type 166 }

-- ONS 15530 Channel 31 or 32 2.5 Gbps ITU Line Card MU with Splitter

cevONS155302p5GCh0102  OBJECT IDENTIFIER
    ::= { cevModuleONS15530Type 167 }

-- ONS 15530 Channel 01 or 02 2.5 Gbps ITU Line Card MU without Splitter

cevONS155302p5GCh0304  OBJECT IDENTIFIER
    ::= { cevModuleONS15530Type 168 }

-- ONS 15530 Channel 03 or 04 2.5 Gbps ITU Line Card MU without Splitter

cevONS155302p5GCh0506  OBJECT IDENTIFIER
    ::= { cevModuleONS15530Type 169 }

-- ONS 15530 Channel 05 or 06 2.5 Gbps ITU Line Card MU without Splitter

cevONS155302p5GCh0708  OBJECT IDENTIFIER
    ::= { cevModuleONS15530Type 170 }

-- ONS 15530 Channel 07 or 08 2.5 Gbps ITU Line Card MU without Splitter

cevONS155302p5GCh0910  OBJECT IDENTIFIER
    ::= { cevModuleONS15530Type 171 }

-- ONS 15530 Channel 09 or 10 2.5 Gbps ITU Line Card MU without Splitter

cevONS155302p5GCh1112  OBJECT IDENTIFIER
    ::= { cevModuleONS15530Type 172 }

-- ONS 15530 Channel 11 or 12 2.5 Gbps ITU Line Card MU without Splitter

cevONS155302p5GCh1314  OBJECT IDENTIFIER
    ::= { cevModuleONS15530Type 173 }

-- ONS 15530 Channel 13 or 14 2.5 Gbps ITU Line Card MU without Splitter

cevONS155302p5GCh1516  OBJECT IDENTIFIER
    ::= { cevModuleONS15530Type 174 }

-- ONS 15530 Channel 15 or 16 2.5 Gbps ITU Line Card MU without Splitter

cevONS155302p5GCh1718  OBJECT IDENTIFIER
    ::= { cevModuleONS15530Type 175 }

-- ONS 15530 Channel 17 or 18 2.5 Gbps ITU Line Card MU without Splitter

cevONS155302p5GCh1920  OBJECT IDENTIFIER
    ::= { cevModuleONS15530Type 176 }

-- ONS 15530 Channel 19 or 20 2.5 Gbps ITU Line Card MU without Splitter

cevONS155302p5GCh2122  OBJECT IDENTIFIER
    ::= { cevModuleONS15530Type 177 }

-- ONS 15530 Channel 21 or 22 2.5 Gbps ITU Line Card MU without Splitter

cevONS155302p5GCh2324  OBJECT IDENTIFIER
    ::= { cevModuleONS15530Type 178 }

-- ONS 15530 Channel 23 or 24 2.5 Gbps ITU Line Card MU without Splitter

cevONS155302p5GCh2526  OBJECT IDENTIFIER
    ::= { cevModuleONS15530Type 179 }

-- ONS 15530 Channel 25 or 26 2.5 Gbps ITU Line Card MU without Splitter

cevONS155302p5GCh2728  OBJECT IDENTIFIER
    ::= { cevModuleONS15530Type 180 }

-- ONS 15530 Channel 27 or 28 2.5 Gbps ITU Line Card MU without Splitter

cevONS155302p5GCh2930  OBJECT IDENTIFIER
    ::= { cevModuleONS15530Type 181 }

-- ONS 15530 Channel 29 or 30 2.5 Gbps ITU Line Card MU without Splitter

cevONS155302p5GCh3132  OBJECT IDENTIFIER
    ::= { cevModuleONS15530Type 182 }

-- ONS 15530 Channel 31 or 32 2.5 Gbps ITU Line Card MU without Splitter

cevONS15530PSM  OBJECT IDENTIFIER
    ::= { cevModuleONS15530Type 183 }

-- ONS 15530 Protection Switch Module

cevONS15530LC2xFC4P  OBJECT IDENTIFIER
    ::= { cevModuleONS15530Type 184 }

-- ONS15530 4-port 2xFC line card

cevONS15530MRC8PCh0102Sp  OBJECT IDENTIFIER
    ::= { cevModuleONS15530Type 185 }

-- ONS 15530 Channel 01 or 02 8-Port Multirate Muxponder card with OC48 trunk and with Splitter

cevONS15530MRC8PCh0304Sp  OBJECT IDENTIFIER
    ::= { cevModuleONS15530Type 186 }

-- ONS 15530 Channel 03 or 04 8-Port Multirate Muxponder card with OC48 trunk and with Splitter

cevONS15530MRC8PCh0506Sp  OBJECT IDENTIFIER
    ::= { cevModuleONS15530Type 187 }

-- ONS 15530 Channel 05 or 06 8-Port Multirate Muxponder card with OC48 trunk and with Splitter

cevONS15530MRC8PCh0708Sp  OBJECT IDENTIFIER
    ::= { cevModuleONS15530Type 188 }

-- ONS 15530 Channel 07 or 08 8-Port Multirate Muxponder card with OC48 trunk and with Splitter

cevONS15530MRC8PCh0910Sp  OBJECT IDENTIFIER
    ::= { cevModuleONS15530Type 189 }

-- ONS 15530 Channel 09 or 10 8-Port Multirate Muxponder card with OC48 trunk and with Splitter

cevONS15530MRC8PCh1112Sp  OBJECT IDENTIFIER
    ::= { cevModuleONS15530Type 190 }

-- ONS 15530 Channel 11 or 12 8-Port Multirate Muxponder card with OC48 trunk and with Splitter

cevONS15530MRC8PCh1314Sp  OBJECT IDENTIFIER
    ::= { cevModuleONS15530Type 191 }

-- ONS 15530 Channel 13 or 14 8-Port Multirate Muxponder card with OC48 trunk and with Splitter

cevONS15530MRC8PCh1516Sp  OBJECT IDENTIFIER
    ::= { cevModuleONS15530Type 192 }

-- ONS 15530 Channel 15 or 16 8-Port Multirate Muxponder card with OC48 trunk and with Splitter

cevONS15530MRC8PCh1718Sp  OBJECT IDENTIFIER
    ::= { cevModuleONS15530Type 193 }

-- ONS 15530 Channel 17 or 18 8-Port Multirate Muxponder card with OC48 trunk and with Splitter

cevONS15530MRC8PCh1920Sp  OBJECT IDENTIFIER
    ::= { cevModuleONS15530Type 194 }

-- ONS 15530 Channel 19 or 20 8-Port Multirate Muxponder card with OC48 trunk and with Splitter

cevONS15530MRC8PCh2122Sp  OBJECT IDENTIFIER
    ::= { cevModuleONS15530Type 195 }

-- ONS 15530 Channel 21 or 22 8-Port Multirate Muxponder card with OC48 trunk and with Splitter

cevONS15530MRC8PCh2324Sp  OBJECT IDENTIFIER
    ::= { cevModuleONS15530Type 196 }

-- ONS 15530 Channel 23 or 24 8-Port Multirate Muxponder card with OC48 trunk and with Splitter

cevONS15530MRC8PCh2526Sp  OBJECT IDENTIFIER
    ::= { cevModuleONS15530Type 197 }

-- ONS 15530 Channel 25 or 26 8-Port Multirate Muxponder card with OC48 trunk and with Splitter

cevONS15530MRC8PCh2728Sp  OBJECT IDENTIFIER
    ::= { cevModuleONS15530Type 198 }

-- ONS 15530 Channel 27 or 28 8-Port Multirate Muxponder card with OC48 trunk and with Splitter

cevONS15530MRC8PCh2930Sp  OBJECT IDENTIFIER
    ::= { cevModuleONS15530Type 199 }

-- ONS 15530 Channel 29 or 30 8-Port Multirate Muxponder card with OC48 trunk and with Splitter

cevONS15530MRC8PCh3132Sp  OBJECT IDENTIFIER
    ::= { cevModuleONS15530Type 200 }

-- ONS 15530 Channel 31 or 32 8-Port Multirate Muxponder card with OC48 trunk and with Splitter

cevONS15530MRC8PCh0102  OBJECT IDENTIFIER
    ::= { cevModuleONS15530Type 201 }

-- ONS 15530 Channel 01 or 02 8-Port Multirate Muxponder card with OC48 trunk and without Splitter

cevONS15530MRC8PCh0304  OBJECT IDENTIFIER
    ::= { cevModuleONS15530Type 202 }

-- ONS 15530 Channel 03 or 04 8-Port Multirate Muxponder card with OC48 trunk and without Splitter

cevONS15530MRC8PCh0506  OBJECT IDENTIFIER
    ::= { cevModuleONS15530Type 203 }

-- ONS 15530 Channel 05 or 06 8-Port Multirate Muxponder card with OC48 trunk and without Splitter

cevONS15530MRC8PCh0708  OBJECT IDENTIFIER
    ::= { cevModuleONS15530Type 204 }

-- ONS 15530 Channel 07 or 08 8-Port Multirate Muxponder card with OC48 trunk and without Splitter

cevONS15530MRC8PCh0910  OBJECT IDENTIFIER
    ::= { cevModuleONS15530Type 205 }

-- ONS 15530 Channel 09 or 10 8-Port Multirate Muxponder card with OC48 trunk and without Splitter

cevONS15530MRC8PCh1112  OBJECT IDENTIFIER
    ::= { cevModuleONS15530Type 206 }

-- ONS 15530 Channel 11 or 12 8-Port Multirate Muxponder card with OC48 trunk and without Splitter

cevONS15530MRC8PCh1314  OBJECT IDENTIFIER
    ::= { cevModuleONS15530Type 207 }

-- ONS 15530 Channel 13 or 14 8-Port Multirate Muxponder card with OC48 trunk and without Splitter

cevONS15530MRC8PCh1516  OBJECT IDENTIFIER
    ::= { cevModuleONS15530Type 208 }

-- ONS 15530 Channel 15 or 16 8-Port Multirate Muxponder card with OC48 trunk and without Splitter

cevONS15530MRC8PCh1718  OBJECT IDENTIFIER
    ::= { cevModuleONS15530Type 209 }

-- ONS 15530 Channel 17 or 18 8-Port Multirate Muxponder card with OC48 trunk and without Splitter

cevONS15530MRC8PCh1920  OBJECT IDENTIFIER
    ::= { cevModuleONS15530Type 210 }

-- ONS 15530 Channel 19 or 20 8-Port Multirate Muxponder card with OC48 trunk and without Splitter

cevONS15530MRC8PCh2122  OBJECT IDENTIFIER
    ::= { cevModuleONS15530Type 211 }

-- ONS 15530 Channel 21 or 22 8-Port Multirate Muxponder card with OC48 trunk and without Splitter

cevONS15530MRC8PCh2324  OBJECT IDENTIFIER
    ::= { cevModuleONS15530Type 212 }

-- ONS 15530 Channel 23 or 24 8-Port Multirate Muxponder card with OC48 trunk and without Splitter

cevONS15530MRC8PCh2526  OBJECT IDENTIFIER
    ::= { cevModuleONS15530Type 213 }

-- ONS 15530 Channel 25 or 26 8-Port Multirate Muxponder card with OC48 trunk and without Splitter

cevONS15530MRC8PCh2728  OBJECT IDENTIFIER
    ::= { cevModuleONS15530Type 214 }

-- ONS 15530 Channel 27 or 28 8-Port Multirate Muxponder card with OC48 trunk and without Splitter

cevONS15530MRC8PCh2930  OBJECT IDENTIFIER
    ::= { cevModuleONS15530Type 215 }

-- ONS 15530 Channel 29 or 30 8-Port Multirate Muxponder card with OC48 trunk and without Splitter

cevONS15530MRC8PCh3132  OBJECT IDENTIFIER
    ::= { cevModuleONS15530Type 216 }

-- ONS 15530 Channel 31 or 32 8-Port Multirate Muxponder card with OC48 trunk and without Splitter

cevONS1553010G4ChASp  OBJECT IDENTIFIER
    ::= { cevModuleONS15530Type 217 }

-- ONS 15530 4-Channel Band A 10Gbps ITU Line Card MU with Splitter

cevONS1553010G4ChBSp  OBJECT IDENTIFIER
    ::= { cevModuleONS15530Type 218 }

-- ONS 15530 4-Channel Band B 10Gbps ITU Line Card MU with Splitter

cevONS1553010G4ChCSp  OBJECT IDENTIFIER
    ::= { cevModuleONS15530Type 219 }

-- ONS 15530 4-Channel Band C 10Gbps ITU Line Card MU with Splitter

cevONS1553010G4ChDSp  OBJECT IDENTIFIER
    ::= { cevModuleONS15530Type 220 }

-- ONS 15530 4-Channel Band D 10Gbps ITU Line Card MU with Splitter

cevONS1553010G4ChESp  OBJECT IDENTIFIER
    ::= { cevModuleONS15530Type 221 }

-- ONS 15530 4-Channel Band E 10Gbps ITU Line Card MU with Splitter

cevONS1553010G4ChFSp  OBJECT IDENTIFIER
    ::= { cevModuleONS15530Type 222 }

-- ONS 15530 4-Channel Band F 10Gbps ITU Line Card MU with Splitter

cevONS1553010G4ChGSp  OBJECT IDENTIFIER
    ::= { cevModuleONS15530Type 223 }

-- ONS 15530 4-Channel Band G 10Gbps ITU Line Card MU with Splitter

cevONS1553010G4ChHSp  OBJECT IDENTIFIER
    ::= { cevModuleONS15530Type 224 }

-- ONS 15530 4-Channel Band H 10Gbps ITU Line Card MU with Splitter

cevONS1553010G4ChA  OBJECT IDENTIFIER
    ::= { cevModuleONS15530Type 225 }

-- ONS 15530 4-Channel Band A 10Gbps ITU Line Card MU without Splitter

cevONS1553010G4ChB  OBJECT IDENTIFIER
    ::= { cevModuleONS15530Type 226 }

-- ONS 15530 4-Channel Band B 10Gbps ITU Line Card MU without Splitter

cevONS1553010G4ChC  OBJECT IDENTIFIER
    ::= { cevModuleONS15530Type 227 }

-- ONS 15530 4-Channel Band C 10Gbps ITU Line Card MU without Splitter

cevONS1553010G4ChD  OBJECT IDENTIFIER
    ::= { cevModuleONS15530Type 228 }

-- ONS 15530 4-Channel Band D 10Gbps ITU Line Card MU without Splitter

cevONS1553010G4ChE  OBJECT IDENTIFIER
    ::= { cevModuleONS15530Type 229 }

-- ONS 15530 4-Channel Band E 10Gbps ITU Line Card MU without Splitter

cevONS1553010G4ChF  OBJECT IDENTIFIER
    ::= { cevModuleONS15530Type 230 }

-- ONS 15530 4-Channel Band F 10Gbps ITU Line Card MU without Splitter

cevONS1553010G4ChG  OBJECT IDENTIFIER
    ::= { cevModuleONS15530Type 231 }

-- ONS 15530 4-Channel Band G 10Gbps ITU Line Card MU without Splitter

cevONS1553010G4ChH  OBJECT IDENTIFIER
    ::= { cevModuleONS15530Type 232 }

-- ONS 15530 4-Channel Band H 10Gbps ITU Line Card MU without Splitter

cevONS1553010G32ChSp  OBJECT IDENTIFIER
    ::= { cevModuleONS15530Type 233 }

-- ONS 15530 32-Channel 10Gbps ITU Line Card MU with Splitter

cevONS1553010G32Ch  OBJECT IDENTIFIER
    ::= { cevModuleONS15530Type 234 }

-- ONS 15530 32-Channel 10Gbps ITU Line Card MU without Splitter

cevModuleONS15500Type  OBJECT IDENTIFIER
    ::= { cevModule 46 }

-- Cisco ONS 15500 modules

cevONS15500PEQ01A  OBJECT IDENTIFIER
    ::= { cevModuleONS15500Type 1 }

-- ONS 15500 Single-Band Power Equalizer Band A

cevONS15500PEQ01B  OBJECT IDENTIFIER
    ::= { cevModuleONS15500Type 2 }

-- ONS 15500 Single-Band Power Equalizer Band B

cevONS15500PEQ01C  OBJECT IDENTIFIER
    ::= { cevModuleONS15500Type 3 }

-- ONS 15500 Single-Band Power Equalizer Band C

cevONS15500PEQ01D  OBJECT IDENTIFIER
    ::= { cevModuleONS15500Type 4 }

-- ONS 15500 Single-Band Power Equalizer Band D

cevONS15500PEQ01E  OBJECT IDENTIFIER
    ::= { cevModuleONS15500Type 5 }

-- ONS 15500 Single-Band Power Equalizer Band E

cevONS15500PEQ01F  OBJECT IDENTIFIER
    ::= { cevModuleONS15500Type 6 }

-- ONS 15500 Single-Band Power Equalizer Band F

cevONS15500PEQ01G  OBJECT IDENTIFIER
    ::= { cevModuleONS15500Type 7 }

-- ONS 15500 Single-Band Power Equalizer Band G

cevONS15500PEQ01H  OBJECT IDENTIFIER
    ::= { cevModuleONS15500Type 8 }

-- ONS 15500 Single-Band Power Equalizer Band H

cevONS15500PEQ02AB  OBJECT IDENTIFIER
    ::= { cevModuleONS15500Type 9 }

-- ONS 15500 Dual Band Power Equalizer Band AB

cevONS15500PEQ02CD  OBJECT IDENTIFIER
    ::= { cevModuleONS15500Type 10 }

-- ONS 15500 Dual Band Power Equalizer Band CD

cevONS15500PEQ02EF  OBJECT IDENTIFIER
    ::= { cevModuleONS15500Type 11 }

-- ONS 15500 Dual Band Power Equalizer Band EF

cevONS15500PEQ02GH  OBJECT IDENTIFIER
    ::= { cevModuleONS15500Type 12 }

-- ONS 15500 Dual Band Power Equalizer Band GH

cevONS15500VOA01  OBJECT IDENTIFIER
    ::= { cevModuleONS15500Type 13 }

-- ONS 15500 One Variable Optical Attenuator

cevONS15500VOA02  OBJECT IDENTIFIER
    ::= { cevModuleONS15500Type 14 }

-- ONS 15500 Two Variable Optical Attenuator

cevONS15500XvrEscon1310MTRJ  OBJECT IDENTIFIER
    ::= { cevModuleONS15500Type 15 }

-- Escon transceiver - 1310nm MM - MTRJ

cevONS15500XvrEscon1310LC  OBJECT IDENTIFIER
    ::= { cevModuleONS15500Type 16 }

-- Escon transceiver - 1310nm MM - LC

cevONS15500XvrFC850LC  OBJECT IDENTIFIER
    ::= { cevModuleONS15500Type 17 }

-- Fibre Channel transceiver - 850nm MM - LC

cevONS15500XvrFC850MTRJ  OBJECT IDENTIFIER
    ::= { cevModuleONS15500Type 18 }

-- Fibre Channel transceiver - 850nm MM - MTRJ

cevONS15500XvrFC1310LC  OBJECT IDENTIFIER
    ::= { cevModuleONS15500Type 19 }

-- Fibre Channel transceiver - 1310nm SM - LC

cevONS15500XvrFC1310MTRJ  OBJECT IDENTIFIER
    ::= { cevModuleONS15500Type 20 }

-- Fibre Channel transceiver - 1310nm SM - MTRJ

cevONS15500XvrGE850LC  OBJECT IDENTIFIER
    ::= { cevModuleONS15500Type 21 }

-- Gigabit Ethernet transceiver - 850nm MM - LC

cevONS15500XvrGE850MTRJ  OBJECT IDENTIFIER
    ::= { cevModuleONS15500Type 22 }

-- Gigabit Ethernet transceiver - 850nm MM - MTRJ

cevONS15500XvrGE1310LC  OBJECT IDENTIFIER
    ::= { cevModuleONS15500Type 23 }

-- Gigabit Ethernet transceiver - 1310nm SM - LC

cevONS15500XvrGE1310MTRJ  OBJECT IDENTIFIER
    ::= { cevModuleONS15500Type 24 }

-- Gigabit Ethernet transceiver - 1310nm SM - MTRJ

cevONS15500XvrGEFC850LC  OBJECT IDENTIFIER
    ::= { cevModuleONS15500Type 25 }

-- G/E transceiver - Fibre Channel - 850nm MM - LC

cevONS15500XvrGEFC850MTRJ  OBJECT IDENTIFIER
    ::= { cevModuleONS15500Type 26 }

-- G/E transceiver - Fibre Channel - 850nm MM - MTRJ

cevONS15500XvrGEFC1310LC  OBJECT IDENTIFIER
    ::= { cevModuleONS15500Type 27 }

-- G/E transceiver - Fibre Channel - 1310nm SM - LC

cevONS15500XvrGEFC1310MTRJ  OBJECT IDENTIFIER
    ::= { cevModuleONS15500Type 28 }

-- G/E transceiver - Fibre Channel - 1310nm SM - MTRJ

cevONS15500XvrOC3Son1310MTRJ  OBJECT IDENTIFIER
    ::= { cevModuleONS15500Type 29 }

-- SONET OC3 transceiver - 1310nm SM - MTRJ

cevONS15500XvrOC3Son1310LC  OBJECT IDENTIFIER
    ::= { cevModuleONS15500Type 30 }

-- SONET OC3 transceiver - 1310nm SM - LC

cevONS15500XvrOC12Son1310MTRJ  OBJECT IDENTIFIER
    ::= { cevModuleONS15500Type 31 }

-- SONET OC12 transceiver - 1310nm SM - MTRJ

cevONS15500XvrOC12Son1310LC  OBJECT IDENTIFIER
    ::= { cevModuleONS15500Type 32 }

-- SONET OC12 transceiver - 1310nm SM - LC

cevONS15500XvrOC48Son1310MTRJ  OBJECT IDENTIFIER
    ::= { cevModuleONS15500Type 33 }

-- SONET OC48 transceiver - 1310nm SM - MTRJ

cevONS15500XvrOC48Son1310LC  OBJECT IDENTIFIER
    ::= { cevModuleONS15500Type 34 }

-- SONET OC48 transceiver - 1310nm SM - LC

cevONS15500XvrLowMM1310LC  OBJECT IDENTIFIER
    ::= { cevModuleONS15500Type 35 }

-- Low band (8-200Mbps) variable rate transceiver - 1310nm Multimode -LC

cevONS15500XvrLowSM1310LC  OBJECT IDENTIFIER
    ::= { cevModuleONS15500Type 36 }

-- Low band (8-200Mbps) variable rate transceiver - 1310nm Singlemode -LC

cevONS15500XvrMidMM1310LC  OBJECT IDENTIFIER
    ::= { cevModuleONS15500Type 37 }

-- Mid band (200-622Mbps) variable rate transceiver - 1310nm Multimode - LC

cevONS15500XvrMidSM1310LC  OBJECT IDENTIFIER
    ::= { cevModuleONS15500Type 38 }

-- Mid band (200-1250Mbps) variable rate transceiver - 1310nm Singlemode - LC

cevONS15500XvrHighSM1310LC  OBJECT IDENTIFIER
    ::= { cevModuleONS15500Type 39 }

-- High band (1.06-2.66Gbps) variable rate transceiver - 1310nm Singlemode - LC

cevONS15500XvrT1  OBJECT IDENTIFIER
    ::= { cevModuleONS15500Type 40 }

-- T1 copper transceiver - RJ45

cevONS15500XvrE1  OBJECT IDENTIFIER
    ::= { cevModuleONS15500Type 41 }

-- E1 copper transceiver - RJ45

cevONS15500XvrDV  OBJECT IDENTIFIER
    ::= { cevModuleONS15500Type 42 }

-- Digital Video copper transceiver - SDI or DVB-ASI - SMB

cevModuleONS15454Type  OBJECT IDENTIFIER
    ::= { cevModule 48 }

-- Cisco ONS 15454 platform

cevONS15454FeCE100  OBJECT IDENTIFIER
    ::= { cevModuleONS15454Type 3 }

-- Cisco ONS 15454 Fast Ethernet Card with 8 Front End Ports

cevONS15454Ge10ML2  OBJECT IDENTIFIER
    ::= { cevModuleONS15454Type 4 }

-- Cisco ONS 15454 Multi-Layer Gigabit Ethernet Card with 10 Front End Ports

cevONS15454Ge10CE2  OBJECT IDENTIFIER
    ::= { cevModuleONS15454Type 5 }

-- Cisco ONS 15454 Gigabit Ethernet Card with 10 Front End Ports

cevONS15454cptPtf25610GX4  OBJECT IDENTIFIER
    ::= { cevModuleONS15454Type 9 }

-- 256G Fabric Card w/ 4x10GE that can be inserted into CPT200 or CPT600 chassis

cevModuleCat37xxType  OBJECT IDENTIFIER
    ::= { cevModule 50 }

-- These are modules that are used in Catalyst 3700 series switches

cevModuleCat375024  OBJECT IDENTIFIER
    ::= { cevModuleCat37xxType 1 }

-- Catalyst 3750 24 Ethernet 10/100 port + 2 Ethernet Gigabit SFP ports module. (SFP: Small Form factor Pluggable).

cevModuleCat375048  OBJECT IDENTIFIER
    ::= { cevModuleCat37xxType 2 }

-- Catalyst 3750 48 Ethernet 10/100 port + 4 Ethernet Gigabit SFP ports module. (SFP: Small Form factor Pluggable).

cevModuleCat375024TS  OBJECT IDENTIFIER
    ::= { cevModuleCat37xxType 3 }

-- Catalyst 3750 24 Ethernet 10/100/1000 port + 4 Ethernet Gigabit SFP ports module. (SFP: Small Form factor Pluggable)

cevModuleCat375024T  OBJECT IDENTIFIER
    ::= { cevModuleCat37xxType 4 }

-- Catalyst 3750 24 Ethernet 10/100/1000 port module. (SFP: Small Form factor Pluggable)

cevModuleCat3750Ge12Sfp  OBJECT IDENTIFIER
    ::= { cevModuleCat37xxType 6 }

-- Catalyst 3750 12 Ethernet Gigabit SFP ports (SFP: Small Form factor Pluggable)

cevModuleCat375048PS  OBJECT IDENTIFIER
    ::= { cevModuleCat37xxType 7 }

-- 48 10/100 In-Line Power Ethernet ports + 2 Gigabit Ethernet SFP ports Layer 2/Layer 3 Module.(SFP Small Form factor Plugable)

cevModuleCat375024PS  OBJECT IDENTIFIER
    ::= { cevModuleCat37xxType 8 }

-- 24 10/100 In-Line Power Ethernet ports + 4 Gigabit Ethernet SFP ports Layer 2/Layer 3 Module.(SFP Small Form factor Plugable)

cevModuleCat375024ME  OBJECT IDENTIFIER
    ::= { cevModuleCat37xxType 9 }

-- Metro Ethernet Catalyst 3750 Module. 24-10/100 + 2 SFP (Small Formfactor Pluggable) ports for downlinks

cevModuleCat3750G16TD  OBJECT IDENTIFIER
    ::= { cevModuleCat37xxType 10 }

-- Catalyst 3750 switch with 16 Ethernet 10/100/1000 ports + one 10 gigabit ethernet port module

cevModuleCat3750G24PS  OBJECT IDENTIFIER
    ::= { cevModuleCat37xxType 11 }

-- Catalyst 3750 24 Power over Ethernet 10/100/1000 port + 4 Ethernet Gigabit SFP ports (SFP: Small Form factor Pluggable)

cevModuleCat3750G48PS  OBJECT IDENTIFIER
    ::= { cevModuleCat37xxType 12 }

-- Catalyst 3750 48 Power over Ethernet 10/100/1000 port + 4 Ethernet Gigabit SFP ports (SFP: Small Form factor Pluggable)

cevModuleCat3750G48TS  OBJECT IDENTIFIER
    ::= { cevModuleCat37xxType 13 }

-- Catalyst 3750 48 Ethernet 10/100/1000 port + 4 Ethernet Gigabit SFP ports (SFP: Small Form factor Pluggable)

cevModuleCat3750G24TS1U  OBJECT IDENTIFIER
    ::= { cevModuleCat37xxType 14 }

-- Catalyst 3750 24 Ethernet 10/100/1000 port + 4 Ethernet Gigabit SFP ports (SFP: Small Form factor Pluggable)

cevModuleCat375024FS  OBJECT IDENTIFIER
    ::= { cevModuleCat37xxType 16 }

-- Catalyst 3750 24 100BaseFX ports + 2 Ethernet Gigabit SFP ports fixed configuration Layer 2/Layer 3 Ethernet switch.   (SFP:Small Formfactor Pluggable)

cevModuleCat3750Ge12SfpDc  OBJECT IDENTIFIER
    ::= { cevModuleCat37xxType 17 }

-- Catalyst 3750 12 Gigabit Ethernet SFP (small Form Factor Plugable) ports

cevModuleCat3750G24WS  OBJECT IDENTIFIER
    ::= { cevModuleCat37xxType 18 }

-- Catalyst 3750 Unified Access Switch with 24 10/100/1000 Power over Ethernet ports + 2 Gigabit Ethernet SFP ports and integrated Wireless Controller. (SFP Small Form factor Pluggable)

cevModuleCat3750E24TD  OBJECT IDENTIFIER
    ::= { cevModuleCat37xxType 19 }

-- Catalyst 3750E 24 10/100/1000 ports + 2 TenGigabit Ethernet (X2) ports

cevModuleCat3750E48TD  OBJECT IDENTIFIER
    ::= { cevModuleCat37xxType 20 }

-- Catalyst 3750E 48 10/100/1000 ports + 2 TenGigabit Ethernet (X2) ports

cevModuleCat3750E48PD  OBJECT IDENTIFIER
    ::= { cevModuleCat37xxType 21 }

-- Catalyst 3750E 48 10/100/1000 Power over Ethernet ports + 2 TenGigabit Ethernet (X2) ports

cevModuleCat3750E24PD  OBJECT IDENTIFIER
    ::= { cevModuleCat37xxType 22 }

-- Catalyst 3750E 24 10/100/1000 Power over Ethernet ports + 2 TenGigabit Ethernet (X2) ports

cevModuleCat3750v248ps  OBJECT IDENTIFIER
    ::= { cevModuleCat37xxType 23 }

-- 48 10/100 ports + 4 Ethernet Gigabit SFP ports fixed configuration Layer 2/Layer 3 Ethernet  Stackable PoE switch

cevModuleCat3750v248ts  OBJECT IDENTIFIER
    ::= { cevModuleCat37xxType 24 }

-- 48 10/100 ports + 4 Ethernet Gigabit SFP ports fixed configuration Layer 2/Layer 3 Ethernet  Stackable switch

cevModuleCat3750v224ps  OBJECT IDENTIFIER
    ::= { cevModuleCat37xxType 25 }

-- 24 10/100 ports + 2 Ethernet Gigabit SFP ports fixed configuration Layer 2/Layer 3 Ethernet  Stackable PoE switch

cevModuleCat3750v224ts  OBJECT IDENTIFIER
    ::= { cevModuleCat37xxType 26 }

-- 24 10/100 ports + 2 Ethernet Gigabit SFP ports fixed configuration Layer 2/Layer 3 Ethernet  Stackable switch

cevModuleCat3750x24  OBJECT IDENTIFIER
    ::= { cevModuleCat37xxType 27 }

-- Catalyst 3750X 24 10/100/1000 Ports + 4 SFP Ports + 2 SFP+ Ports Layer 2/Layer 3 Ethernet Stackable Switch

cevModuleCat3750x48  OBJECT IDENTIFIER
    ::= { cevModuleCat37xxType 28 }

-- Catalyst 3750X 48 10/100/1000 Ports + 4 SFP Ports + 2 SFP+ Ports Layer 2/Layer 3 Ethernet Stackable Switch

cevModuleCat3750x24P  OBJECT IDENTIFIER
    ::= { cevModuleCat37xxType 29 }

-- Catalyst 3750X 24 10/100/1000 PoE Ports + 4 SFP Ports + 2 SFP+ Ports Layer 2/Layer 3 Ethernet Stackable Switch

cevModuleCat3750x48P  OBJECT IDENTIFIER
    ::= { cevModuleCat37xxType 30 }

-- Catalyst 3750X 48 10/100/1000 PoE Ports + 4 SFP Ports + 2 SFP+ Ports Layer 2/Layer 3 Ethernet Stackable Switch

cevModuleSFPType  OBJECT IDENTIFIER
    ::= { cevModule 51 }

-- Represents the base class for all SFP modules.

cevSFPOc3mm  OBJECT IDENTIFIER
    ::= { cevModuleSFPType 1 }

-- Oc3 Small Form Factor Pluggable Optics(SFP)

cevSFPOc12mm  OBJECT IDENTIFIER
    ::= { cevModuleSFPType 2 }

-- Oc12 Small Form Factor Pluggable Optics(SFP)

cevSFPOc48  OBJECT IDENTIFIER
    ::= { cevModuleSFPType 3 }

-- OC48 Small Form Factor Pluggable Optics(SFP)

cevSFPOc3Oc12  OBJECT IDENTIFIER
    ::= { cevModuleSFPType 4 }

-- Dual rate OC3/OC12 Small Form Factor Pluggable Optics(SFP)

cevSFPOc3Oc12Oc48  OBJECT IDENTIFIER
    ::= { cevModuleSFPType 5 }

-- Multi-rate OC3/OC12/OC48 Small Form Factor Pluggable Optics(SFP)

cevSFP1000BaseSx  OBJECT IDENTIFIER
    ::= { cevModuleSFPType 6 }

-- Short wavelength gigabit ethernet SFP.

cevSFP1000BaseLx  OBJECT IDENTIFIER
    ::= { cevModuleSFPType 7 }

-- Long wavelength gigabit ethernet SFP.

cevSFP1000BaseT  OBJECT IDENTIFIER
    ::= { cevModuleSFPType 8 }

-- copper gigabit ethernet SFP.

cevSFP1000BaseZx  OBJECT IDENTIFIER
    ::= { cevModuleSFPType 9 }

-- Extended reach gigabit ethernet SFP.

cevSFPCwdm1470  OBJECT IDENTIFIER
    ::= { cevModuleSFPType 10 }

-- 1470nm color coded CWDM SFP.

cevSFPCwdm1490  OBJECT IDENTIFIER
    ::= { cevModuleSFPType 11 }

-- 1490nm color coded CWDM SFP.

cevSFPCwdm1510  OBJECT IDENTIFIER
    ::= { cevModuleSFPType 12 }

-- 1510nm color coded CWDM SFP.

cevSFPCwdm1530  OBJECT IDENTIFIER
    ::= { cevModuleSFPType 13 }

-- 1530nm color coded CWDM SFP.

cevSFPCwdm1550  OBJECT IDENTIFIER
    ::= { cevModuleSFPType 14 }

-- 1550nm color coded CWDM SFP.

cevSFPCwdm1570  OBJECT IDENTIFIER
    ::= { cevModuleSFPType 15 }

-- 1570nm color coded CWDM SFP.

cevSFPCwdm1590  OBJECT IDENTIFIER
    ::= { cevModuleSFPType 16 }

-- 1590nm color coded CWDM SFP.

cevSFPCwdm1610  OBJECT IDENTIFIER
    ::= { cevModuleSFPType 17 }

-- 1610nm color coded CWDM SFP.

cevSFP1000BaseLh  OBJECT IDENTIFIER
    ::= { cevModuleSFPType 18 }

-- long haul gigabit ethernet SFP.

cevSFP1000BaseCx  OBJECT IDENTIFIER
    ::= { cevModuleSFPType 19 }

-- copper wire gigabit ethernet SFP.

cevSFPOc3smir  OBJECT IDENTIFIER
    ::= { cevModuleSFPType 20 }

-- OC3 Single Mode Intermediate Reach SFP

cevSFPOc3smlr  OBJECT IDENTIFIER
    ::= { cevModuleSFPType 21 }

-- OC3 Single Mode Long Reach SFP

cevSFPOc12smir  OBJECT IDENTIFIER
    ::= { cevModuleSFPType 22 }

-- OC12 Single Mode Intermediate Reach SFP

cevSFPOc12smlr  OBJECT IDENTIFIER
    ::= { cevModuleSFPType 23 }

-- OC12 Single Mode Long Reach SFP

cevSFPOc48smsr  OBJECT IDENTIFIER
    ::= { cevModuleSFPType 24 }

-- OC48 Single Mode Short Reach SFP

cevSFPOc48smir  OBJECT IDENTIFIER
    ::= { cevModuleSFPType 25 }

-- OC48 Single Mode Intermediate Reach SFP

cevSFPOc48smlr  OBJECT IDENTIFIER
    ::= { cevModuleSFPType 26 }

-- OC48 Single Mode Long Reach SFP

cevXFPOc192smsr1  OBJECT IDENTIFIER
    ::= { cevModuleSFPType 27 }

-- OC192 XFP Single Mode Short Reach 1 (2km).

cevXFPOc192smir2  OBJECT IDENTIFIER
    ::= { cevModuleSFPType 28 }

-- OC192 XFP Single Mode Intermediate Reach 2 (40km).

cevXFPOc192smlr2  OBJECT IDENTIFIER
    ::= { cevModuleSFPType 29 }

-- OC192 XFP Single Mode Long Reach 2 (80km).

cevSFPCable50cm  OBJECT IDENTIFIER
    ::= { cevModuleSFPType 30 }

-- SFP patch cable, 50cm (centimeters)

cevSFPOc48smlr2  OBJECT IDENTIFIER
    ::= { cevModuleSFPType 33 }

-- 1-port OC48 Small form Factor Pluggable (SFP) Long Reach (LR-2)

cevSFPOc3smsr  OBJECT IDENTIFIER
    ::= { cevModuleSFPType 34 }

-- Oc3 Single Mode, Short Reach, Small Form Factor Pluggable Optics(SFP)

cevSFPOc12smsr  OBJECT IDENTIFIER
    ::= { cevModuleSFPType 35 }

-- OC12 Single Mode, Short Reach, Small Form Factor Pluggable Optics(SFP)

cevSFPOc48mm  OBJECT IDENTIFIER
    ::= { cevModuleSFPType 36 }

-- OC48 Multi Mode, Small Form Factor Pluggable Optics(SFP)

cevSFPDwdm3033  OBJECT IDENTIFIER
    ::= { cevModuleSFPType 37 }

-- MOD,XCVR,2.5Gb/s,1530.33nm,SM,LR2,3.3V,0 to 70C,LC,SFP,DIGITAL DIAGS FIM32160/201W59

cevSFPDwdm3112  OBJECT IDENTIFIER
    ::= { cevModuleSFPType 38 }

-- MOD,XCVR,2.5Gb/s,1531.12nm,SM,LR2,3.3V,0 to 70C,LC,SFP,DIGITAL DIAGS FIM32160/201W58

cevSFPDwdm3190  OBJECT IDENTIFIER
    ::= { cevModuleSFPType 39 }

-- MOD,XCVR,2.5Gb/s,1531.90nm,SM,LR2,3.3V,0 to 70C,LC,SFP,DIGITAL DIAGS FIM32160/201W57

cevSFPDwdm3268  OBJECT IDENTIFIER
    ::= { cevModuleSFPType 40 }

-- MOD,XCVR,2.5Gb/s,1532.68nm,SM,LR2,3.3V,0 to 70C,LC,SFP,DIGITAL DIAGS FIM32160/201W56

cevSFPDwdm3425  OBJECT IDENTIFIER
    ::= { cevModuleSFPType 41 }

-- MOD,XCVR,2.5Gb/s,1534.25nm,SM,LR2,3.3V,0 to 70C,LC,SFP,DIGITAL DIAGS FIM32160/201W54

cevSFPDwdm3504  OBJECT IDENTIFIER
    ::= { cevModuleSFPType 42 }

-- MOD,XCVR,2.5Gb/s,1535.04nm,SM,LR2,3.3V,0 to 70C,LC,SFP,DIGITAL DIAGS FIM32160/201W53

cevSFPDwdm3582  OBJECT IDENTIFIER
    ::= { cevModuleSFPType 43 }

-- MOD,XCVR,2.5Gb/s,1535.82nm,SM,LR2,3.3V,0 to 70C,LC,SFP,DIGITAL DIAGS FIM32160/201W52

cevSFPDwdm3661  OBJECT IDENTIFIER
    ::= { cevModuleSFPType 44 }

-- MOD,XCVR,2.5Gb/s,1536.61nm,SM,LR2,3.3V,0 to 70C,LC,SFP,DIGITAL DIAGS FIM32160/201W51

cevSFPDwdm3819  OBJECT IDENTIFIER
    ::= { cevModuleSFPType 45 }

-- MOD,XCVR,2.5Gb/s,1538.19nm,SM,LR2,3.3V,0 to 70C,LC,SFP,DIGITAL DIAGS FIM32160/201W49

cevSFPDwdm3898  OBJECT IDENTIFIER
    ::= { cevModuleSFPType 46 }

-- MOD,XCVR,2.5Gb/s,1538.98nm,SM,LR2,3.3V,0 to 70C,LC,SFP,DIGITAL DIAGS FIM32160/201W48

cevSFPDwdm3977  OBJECT IDENTIFIER
    ::= { cevModuleSFPType 47 }

-- MOD,XCVR,2.5Gb/s,1539.77nm,SM,LR2,3.3V,0 to 70C,LC,SFP,DIGITAL DIAGS FIM32160/201W47

cevSFPDwdm4056  OBJECT IDENTIFIER
    ::= { cevModuleSFPType 48 }

-- MOD,XCVR,2.5Gb/s,1540.56nm,SM,LR2,3.3V,0 to 70C,LC,SFP,DIGITAL DIAGS FIM32160/201W46

cevSFPDwdm4214  OBJECT IDENTIFIER
    ::= { cevModuleSFPType 49 }

-- MOD,XCVR,2.5Gb/s,1542.14nm,SM,LR2,3.3V,0 to 70C,LC,SFP,DIGITAL DIAGS FIM32160/201W44

cevSFPDwdm4294  OBJECT IDENTIFIER
    ::= { cevModuleSFPType 50 }

-- MOD,XCVR,2.5Gb/s,1542.94nm,SM,LR2,3.3V,0 to 70C,LC,SFP,DIGITAL DIAGS FIM32160/201W43

cevSFPDwdm4373  OBJECT IDENTIFIER
    ::= { cevModuleSFPType 51 }

-- MOD,XCVR,2.5Gb/s,1543.73nm,SM,LR2,3.3V,0 to 70C,LC,SFP,DIGITAL DIAGS FIM32160/201W42

cevSFPDwdm4453  OBJECT IDENTIFIER
    ::= { cevModuleSFPType 52 }

-- MOD,XCVR,2.5Gb/s,1544.53nm,SM,LR2,3.3V,0 to 70C,LC,SFP,DIGITAL DIAGS FIM32160/201W41

cevSFPDwdm4612  OBJECT IDENTIFIER
    ::= { cevModuleSFPType 53 }

-- MOD,XCVR,2.5Gb/s,1546.12nm,SM,LR2,3.3V,0 to 70C,LC,SFP,DIGITAL DIAGS FIM32160/201W39

cevSFPDwdm4692  OBJECT IDENTIFIER
    ::= { cevModuleSFPType 54 }

-- MOD,XCVR,2.5Gb/s,1546.92nm,SM,LR2,3.3V,0 to 70C,LC,SFP,DIGITAL DIAGS FIM32160/201W38

cevSFPDwdm4772  OBJECT IDENTIFIER
    ::= { cevModuleSFPType 55 }

-- MOD,XCVR,2.5Gb/s,1547.72nm,SM,LR2,3.3V,0 to 70C,LC,SFP,DIGITAL DIAGS FIM32160/201W37

cevSFPDwdm4851  OBJECT IDENTIFIER
    ::= { cevModuleSFPType 56 }

-- MOD,XCVR,2.5Gb/s,1548.51nm,SM,LR2,3.3V,0 to 70C,LC,SFP,DIGITAL DIAGS FIM32160/201W36

cevSFPDwdm5012  OBJECT IDENTIFIER
    ::= { cevModuleSFPType 57 }

-- MOD,XCVR,2.5Gb/s,1550.12nm,SM,LR2,3.3V,0 to 70C,LC,SFP,DIGITAL DIAGS FIM32160/201W34

cevSFPDwdm5092  OBJECT IDENTIFIER
    ::= { cevModuleSFPType 58 }

-- MOD,XCVR,2.5Gb/s,1550.92nm,SM,LR2,3.3V,0 to 70C,LC,SFP,DIGITAL DIAGS FIM32160/201W33

cevSFPDwdm5172  OBJECT IDENTIFIER
    ::= { cevModuleSFPType 59 }

-- MOD,XCVR,2.5Gb/s,1551.72nm,SM,LR2,3.3V,0 to 70C,LC,SFP,DIGITAL DIAGS FIM32160/201W32

cevSFPDwdm5252  OBJECT IDENTIFIER
    ::= { cevModuleSFPType 60 }

-- MOD,XCVR,2.5Gb/s,1552.52nm,SM,LR2,3.3V,0 to 70C,LC,SFP,DIGITAL DIAGS FIM32160/201W31

cevSFPDwdm5413  OBJECT IDENTIFIER
    ::= { cevModuleSFPType 61 }

-- MOD,XCVR,2.5Gb/s,1554.13nm,SM,LR2,3.3V,0 to 70C,LC,SFP,DIGITAL DIAGS FIM32160/201W29

cevSFPDwdm5494  OBJECT IDENTIFIER
    ::= { cevModuleSFPType 62 }

-- MOD,XCVR,2.5Gb/s,1554.94nm,SM,LR2,3.3V,0 to 70C,LC,SFP,DIGITAL DIAGS FIM32160/201W28

cevSFPDwdm5575  OBJECT IDENTIFIER
    ::= { cevModuleSFPType 63 }

-- MOD,XCVR,2.5Gb/s,1555.75nm,SM,LR2,3.3V,0 to 70C,LC,SFP,DIGITAL DIAGS FIM32160/201W27

cevSFPDwdm5655  OBJECT IDENTIFIER
    ::= { cevModuleSFPType 64 }

-- MOD,XCVR,2.5Gb/s,1556.55nm,SM,LR2,3.3V,0 to 70C,LC,SFP,DIGITAL DIAGS FIM32160/201W26

cevSFPDwdm5817  OBJECT IDENTIFIER
    ::= { cevModuleSFPType 65 }

-- MOD,XCVR,2.5Gb/s,1558.17nm,SM,LR2,3.3V,0 to 70C,LC,SFP,DIGITAL DIAGS FIM32160/201W24

cevSFPDwdm5898  OBJECT IDENTIFIER
    ::= { cevModuleSFPType 66 }

-- MOD,XCVR,2.5Gb/s,1558.98nm,SM,LR2,3.3V,0 to 70C,LC,SFP,DIGITAL DIAGS FIM32160/201W23

cevSFPDwdm5979  OBJECT IDENTIFIER
    ::= { cevModuleSFPType 67 }

-- MOD,XCVR,2.5Gb/s,1559.79nm,SM,LR2,3.3V,0 to 70C,LC,SFP,DIGITAL DIAGS FIM32160/201W22

cevSFPDwdm6061  OBJECT IDENTIFIER
    ::= { cevModuleSFPType 68 }

-- MOD,XCVR,2.5Gb/s,1560.61nm,SM,LR2,3.3V,0 to 70C,LC,SFP,DIGITAL DIAGS FIM32160/201W21

cevSFP1000BaseBX10D  OBJECT IDENTIFIER
    ::= { cevModuleSFPType 69 }

-- 1000BASE-BX10-D downstream bidirectional single fiber SFP

cevSFP1000BaseBX10U  OBJECT IDENTIFIER
    ::= { cevModuleSFPType 70 }

-- 1000BASE-BX10-U upstream bidirectional single fiber SFP

cevSFP100BaseFX  OBJECT IDENTIFIER
    ::= { cevModuleSFPType 71 }

-- 100BASE-FX SFP

cevSFP100BaseLX  OBJECT IDENTIFIER
    ::= { cevModuleSFPType 72 }

-- 100BASE-LX SFP

cevSFP100BaseSX  OBJECT IDENTIFIER
    ::= { cevModuleSFPType 73 }

-- 100BASE-SX SFP

cevSFP100BaseZX  OBJECT IDENTIFIER
    ::= { cevModuleSFPType 74 }

-- 100BASE-ZX SFP

cevSFP100BaseEX  OBJECT IDENTIFIER
    ::= { cevModuleSFPType 75 }

-- 100BASE-EX SFP

cevSFP100BaseBX10D  OBJECT IDENTIFIER
    ::= { cevModuleSFPType 76 }

-- 100BASE-BX10-D downstream bidirectional single fiber SFP

cevSFP100BaseBX10U  OBJECT IDENTIFIER
    ::= { cevModuleSFPType 77 }

-- 100BASE-BX10-U upstream bidirectional single fiber SFP

cevSFPDwdmXFP6061  OBJECT IDENTIFIER
    ::= { cevModuleSFPType 78 }

-- DWDM XFP 1560.61 nm XFP (100 GHz ITU grid)

cevSFPDwdmXFP5979  OBJECT IDENTIFIER
    ::= { cevModuleSFPType 79 }

-- DWDM XFP 1559.79 nm XFP (100 GHz ITU grid)

cevSFPDwdmXFP5898  OBJECT IDENTIFIER
    ::= { cevModuleSFPType 80 }

-- DWDM XFP 1558.98 nm XFP (100 GHz ITU grid)

cevSFPDwdmXFP5817  OBJECT IDENTIFIER
    ::= { cevModuleSFPType 81 }

-- DWDM XFP 1558.17 nm XFP (100 GHz ITU grid)

cevSFPDwdmXFP5655  OBJECT IDENTIFIER
    ::= { cevModuleSFPType 82 }

-- DWDM XFP 1556.55 nm XFP (100 GHz ITU grid)

cevSFPDwdmXFP5575  OBJECT IDENTIFIER
    ::= { cevModuleSFPType 83 }

-- DWDM XFP 1555.75 nm XFP (100 GHz ITU grid)

cevSFPDwdmXFP5494  OBJECT IDENTIFIER
    ::= { cevModuleSFPType 84 }

-- DWDM XFP 1554.94 nm XFP (100 GHz ITU grid)

cevSFPDwdmXFP5413  OBJECT IDENTIFIER
    ::= { cevModuleSFPType 85 }

-- DWDM XFP 1554.13 nm XFP (100 GHz ITU grid)

cevSFPDwdmXFP5252  OBJECT IDENTIFIER
    ::= { cevModuleSFPType 86 }

-- DWDM XFP 1552.52 nm XFP (100 GHz ITU grid)

cevSFPDwdmXFP5172  OBJECT IDENTIFIER
    ::= { cevModuleSFPType 87 }

-- DWDM XFP 1551.72 nm XFP (100 GHz ITU grid)

cevSFPDwdmXFP5092  OBJECT IDENTIFIER
    ::= { cevModuleSFPType 88 }

-- DWDM XFP 1550.92 nm XFP (100 GHz ITU grid)

cevSFPDwdmXFP5012  OBJECT IDENTIFIER
    ::= { cevModuleSFPType 89 }

-- DWDM XFP 1550.12 nm XFP (100 GHz ITU grid)

cevSFPDwdmXFP4851  OBJECT IDENTIFIER
    ::= { cevModuleSFPType 90 }

-- DWDM XFP 1548.51 nm XFP (100 GHz ITU grid)

cevSFPDwdmXFP4772  OBJECT IDENTIFIER
    ::= { cevModuleSFPType 91 }

-- DWDM XFP 1547.72 nm XFP (100 GHz ITU grid)

cevSFPDwdmXFP4692  OBJECT IDENTIFIER
    ::= { cevModuleSFPType 92 }

-- DWDM XFP 1546.92 nm XFP (100 GHz ITU grid)

cevSFPDwdmXFP4612  OBJECT IDENTIFIER
    ::= { cevModuleSFPType 93 }

-- DWDM XFP 1546.12 nm XFP (100 GHz ITU grid)

cevSFPDwdmXFP4453  OBJECT IDENTIFIER
    ::= { cevModuleSFPType 94 }

-- DWDM XFP 1544.53 nm XFP (100 GHz ITU grid)

cevSFPDwdmXFP4373  OBJECT IDENTIFIER
    ::= { cevModuleSFPType 95 }

-- DWDM XFP 1543.73 nm XFP (100 GHz ITU grid)

cevSFPDwdmXFP4294  OBJECT IDENTIFIER
    ::= { cevModuleSFPType 96 }

-- DWDM XFP 1542.94 nm XFP (100 GHz ITU grid)

cevSFPDwdmXFP4214  OBJECT IDENTIFIER
    ::= { cevModuleSFPType 97 }

-- DWDM XFP 1542.14 nm XFP (100 GHz ITU grid)

cevSFPDwdmXFP4056  OBJECT IDENTIFIER
    ::= { cevModuleSFPType 98 }

-- DWDM XFP 1540.56 nm XFP (100 GHz ITU grid)

cevSFPDwdmXFP3977  OBJECT IDENTIFIER
    ::= { cevModuleSFPType 99 }

-- DWDM XFP 1539.77 nm XFP (100 GHz ITU grid)

cevSFPDwdmXFP3898  OBJECT IDENTIFIER
    ::= { cevModuleSFPType 100 }

-- DWDM XFP 1538.98 nm XFP (100 GHz ITU grid)

cevSFPDwdmXFP3819  OBJECT IDENTIFIER
    ::= { cevModuleSFPType 101 }

-- DWDM XFP 1538.19 nm XFP (100 GHz ITU grid)

cevSFPDwdmXFP3661  OBJECT IDENTIFIER
    ::= { cevModuleSFPType 102 }

-- DWDM XFP 1536.61 nm XFP (100 GHz ITU grid)

cevSFPDwdmXFP3582  OBJECT IDENTIFIER
    ::= { cevModuleSFPType 103 }

-- DWDM XFP 1535.82 nm XFP (100 GHz ITU grid)

cevSFPDwdmXFP3504  OBJECT IDENTIFIER
    ::= { cevModuleSFPType 104 }

-- DWDM XFP 1535.04 nm XFP (100 GHz ITU grid)

cevSFPDwdmXFP3425  OBJECT IDENTIFIER
    ::= { cevModuleSFPType 105 }

-- DWDM XFP 1534.25 nm XFP (100 GHz ITU grid)

cevSFPDwdmXFP3268  OBJECT IDENTIFIER
    ::= { cevModuleSFPType 106 }

-- DWDM XFP 1532.68 nm XFP (100 GHz ITU grid)

cevSFPDwdmXFP3190  OBJECT IDENTIFIER
    ::= { cevModuleSFPType 107 }

-- DWDM XFP 1531.90 nm XFP (100 GHz ITU grid)

cevSFPDwdmXFP3112  OBJECT IDENTIFIER
    ::= { cevModuleSFPType 108 }

-- DWDM XFP 1531.12 nm XFP (100 GHz ITU grid)

cevSFPDwdmXFP3033  OBJECT IDENTIFIER
    ::= { cevModuleSFPType 109 }

-- DWDM XFP 1530.33 nm XFP (100 GHz ITU grid)

cevSFPDwdm6141  OBJECT IDENTIFIER
    ::= { cevModuleSFPType 110 }

-- Cisco 1000BASE-DWDM SFP 1561.41nm

cevSFPDwdm5736  OBJECT IDENTIFIER
    ::= { cevModuleSFPType 111 }

-- Cisco 1000BASE-DWDM SFP 1557.36nm

cevSFPDwdm5332  OBJECT IDENTIFIER
    ::= { cevModuleSFPType 112 }

-- Cisco 1000BASE-DWDM SFP 1553.32nm

cevSFPDwdm4931  OBJECT IDENTIFIER
    ::= { cevModuleSFPType 113 }

-- Cisco 1000BASE-DWDM SFP 1549.31nm

cevSFPDwdm4532  OBJECT IDENTIFIER
    ::= { cevModuleSFPType 114 }

-- Cisco 1000BASE-DWDM SFP 1545.32nm

cevSFPDwdm4134  OBJECT IDENTIFIER
    ::= { cevModuleSFPType 115 }

-- Cisco 1000BASE-DWDM SFP 1541.34nm

cevSFPDwdm3739  OBJECT IDENTIFIER
    ::= { cevModuleSFPType 116 }

-- Cisco 1000BASE-DWDM SFP 1537.39nm

cevSFPDwdm3346  OBJECT IDENTIFIER
    ::= { cevModuleSFPType 117 }

-- Cisco 1000BASE-DWDM SFP 1533.46nm

cevSFPUnknown  OBJECT IDENTIFIER
    ::= { cevModuleSFPType 118 }

-- Unknown SFP

cevXFPUnknown  OBJECT IDENTIFIER
    ::= { cevModuleSFPType 119 }

-- Unknown XFP

cevSFPStm1E  OBJECT IDENTIFIER
    ::= { cevModuleSFPType 120 }

-- Small Form-factor Pluggable (SFP) STM-1 electrical transceiver

cevXFPmmsr  OBJECT IDENTIFIER
    ::= { cevModuleSFPType 121 }

-- Multirate 10GBASE-SR, SMF

cevXFR10gMMSR  OBJECT IDENTIFIER
    ::= { cevModuleSFPType 122 }

-- 10Gigabit XFP Multi Mode Short Reach

cevSFPTDwdmXfp  OBJECT IDENTIFIER
    ::= { cevModuleSFPType 123 }

-- Tunable Wavelength Dwdm Xfp, Wavelength 1529.55 to 1561.83,Channel number 1 to 82

cevXFP10GLR192SRL  OBJECT IDENTIFIER
    ::= { cevModuleSFPType 124 }

-- 10GE Long Reach / OC192 Short Reach Low Power Single Mode XFP(10KM)

cevXFP10GER192IRL  OBJECT IDENTIFIER
    ::= { cevModuleSFPType 125 }

-- 10GE Extended Reach / OC192 Intermediate Reach Low Power Single Mode XFP (40KM)

cevSFPCiscoSfpT3Ge  OBJECT IDENTIFIER
    ::= { cevModuleSFPType 126 }

-- GE to T3 SFP module

cevSFPT1E1Fe  OBJECT IDENTIFIER
    ::= { cevModuleSFPType 127 }

-- FE over T1/E1 SFP Module.

cevSFPT3E3Fe  OBJECT IDENTIFIER
    ::= { cevModuleSFPType 128 }

-- FE over T3/E3 SFP Module

cevXFPDWDMXFPC  OBJECT IDENTIFIER
    ::= { cevModuleSFPType 129 }

-- 10G MultiRate C Band Tunable DWDM XFP

cevXFP10GLROC192  OBJECT IDENTIFIER
    ::= { cevModuleSFPType 130 }

-- Multirate XFP module for 10GBASE-LR and OC192 SR-1

cevXFP10GER192IR  OBJECT IDENTIFIER
    ::= { cevModuleSFPType 131 }

-- Cisco Multirate 10GBASE-ER and OC-192/STM-64 IR-2 XFP Module

cevXFP10GZROC192  OBJECT IDENTIFIER
    ::= { cevModuleSFPType 132 }

-- 10GBASE-ZR and OC192 LR2 XFP Module

cevXFP10GMMSR  OBJECT IDENTIFIER
    ::= { cevModuleSFPType 133 }

-- 10GBASE-SR XFP Module

cevSFPGLC2BXD  OBJECT IDENTIFIER
    ::= { cevModuleSFPType 134 }

-- 1000BASE-BX10 SFP, 1490NM, 2-Channels

cevSFPGLC2BXU  OBJECT IDENTIFIER
    ::= { cevModuleSFPType 135 }

-- 1000BASE-BX10 SFP, 1310NM, 2-Channels

cevSFPGLCFE1002BX  OBJECT IDENTIFIER
    ::= { cevModuleSFPType 136 }

-- 100BASE-BX10 SFP, 1490NM, 2-Channels

cevSFPGLCFE1002BXU  OBJECT IDENTIFIER
    ::= { cevModuleSFPType 137 }

-- 100BASE-BX10 SFP, 1310NM, 2-Channels

cevSFPGlcSxMmd  OBJECT IDENTIFIER
    ::= { cevModuleSFPType 138 }

-- GLC-SX-MMD:Catskill optics PID

cevSFPGlcTe  OBJECT IDENTIFIER
    ::= { cevModuleSFPType 139 }

-- GLC-TE:Catskill optics PID

cevSFPGlcZxSmd  OBJECT IDENTIFIER
    ::= { cevModuleSFPType 140 }

-- GLC-ZX-SMD:Catskill optics PID

cevSFPGlcExSmd  OBJECT IDENTIFIER
    ::= { cevModuleSFPType 141 }

-- GLC-EX-SMD:Catskill optics PID

cevSFPGlcLhSmd  OBJECT IDENTIFIER
    ::= { cevModuleSFPType 142 }

-- GLC-LH-SMD:Catskill optics PID

cevSFP100BaseF  OBJECT IDENTIFIER
    ::= { cevModuleSFPType 143 }

-- 100BASE-F SFP

cevSFPDSSFPFC16GSW  OBJECT IDENTIFIER
    ::= { cevModuleSFPType 144 }

-- DS-SFP-FC16G-SW, 16G SW Optics for MDS 10-Slot Director Switch,DS9710

cevSFDSSFPFC16GLW  OBJECT IDENTIFIER
    ::= { cevModuleSFPType 145 }

-- DS-SFP-FC16G-LW, 16G LW Optics for MDS 10-Slot Director Switch,DS9710

cevSFPGLCGE100FX  OBJECT IDENTIFIER
    ::= { cevModuleSFPType 146 }

-- 100FX SFP on GE ports

cevSFPCwdmXFP1570  OBJECT IDENTIFIER
    ::= { cevModuleSFPType 147 }

-- Cisco XFP transceiver module, 1570nm wavelength, color coded CWDM XFP

cevSFPCwdmXFP1470  OBJECT IDENTIFIER
    ::= { cevModuleSFPType 148 }

-- Cisco XFP transceiver module, 1470nm wavelength, color coded CWDM XFP

cevSFPCwdmXFP1490  OBJECT IDENTIFIER
    ::= { cevModuleSFPType 149 }

-- Cisco XFP transceiver module, 1490nm wavelength, color coded CWDM XFP

cevSFPCwdmXFP1510  OBJECT IDENTIFIER
    ::= { cevModuleSFPType 150 }

-- Cisco XFP transceiver module, 1510nm wavelength, color coded CWDM XFP

cevSFPCwdmXFP1530  OBJECT IDENTIFIER
    ::= { cevModuleSFPType 151 }

-- Cisco XFP transceiver module, 1530nm wavelength, color coded CWDM XFP

cevSFPCwdmXFP1550  OBJECT IDENTIFIER
    ::= { cevModuleSFPType 152 }

-- Cisco XFP transceiver module, 1550nm wavelength, color coded CWDM XFP

cevSFPCwdmXFP1590  OBJECT IDENTIFIER
    ::= { cevModuleSFPType 153 }

-- Cisco XFP transceiver module, 1590nm wavelength, color coded CWDM XFP

cevSFPCwdmXFP1610  OBJECT IDENTIFIER
    ::= { cevModuleSFPType 154 }

-- Cisco XFP transceiver module, 1610nm wavelength, color coded CWDM XFP

cevSFP1000BaseBX40D  OBJECT IDENTIFIER
    ::= { cevModuleSFPType 155 }

-- 1000BASE-BX40-D downstream bidirectional single fiber SFP

cevSFP1000BaseBX40U  OBJECT IDENTIFIER
    ::= { cevModuleSFPType 156 }

-- 1000BASE-BX40-U upstream bidirectional single fiber SFP

cevSFP1000BaseBX80D  OBJECT IDENTIFIER
    ::= { cevModuleSFPType 157 }

-- 1000BASE-BX80-D downstream bidirectional single fiber SFP

cevSFP1000BaseBX80U  OBJECT IDENTIFIER
    ::= { cevModuleSFPType 158 }

-- 1000BASE-BX80-U upstream bidirectional single fiber SFP

cevSFP100BaseGlcExFe  OBJECT IDENTIFIER
    ::= { cevModuleSFPType 159 }

-- FE 100BASE-EX SFP, SMF, 40Km

cevSFP100BaseGlcZxFe  OBJECT IDENTIFIER
    ::= { cevModuleSFPType 160 }

-- FE 100BASE-ZX SFP, SMF, 80Km

cevModuleONS15200Type  OBJECT IDENTIFIER
    ::= { cevModule 52 }

-- Represents the base class for all the modules used in ONS15200.

cevONS15252Clip  OBJECT IDENTIFIER
    ::= { cevModuleONS15200Type 1 }

-- ONS15252 Client Line Interface Port

cevONS15201Clip  OBJECT IDENTIFIER
    ::= { cevModuleONS15200Type 2 }

-- ONS15201 Client Line Interface Port

cevONS15252Ncb  OBJECT IDENTIFIER
    ::= { cevModuleONS15200Type 3 }

-- ONS15252 Network Controller Board

cevModuleMDSType  OBJECT IDENTIFIER
    ::= { cevModule 53 }

-- Represents the base class for all the modules used in MDS.

cevMDSDsX9530Sf1K9  OBJECT IDENTIFIER
    ::= { cevModuleMDSType 1 }

-- DS-X9530-SF1-K9  - MDS 9500 Supervisor/Fabric 1

cevMDSRedDsX9530Sf1K9  OBJECT IDENTIFIER
    ::= { cevModuleMDSType 2 }

-- DS-X9530-SF1-K9  - MDS 9500 Supervisor/Fabric 1, Redundant

cevMDSDsX9016  OBJECT IDENTIFIER
    ::= { cevModuleMDSType 3 }

-- DS-X9016   - MDS 9500 16-port 1/2Gbps FC Module

cevMDSDsX9032  OBJECT IDENTIFIER
    ::= { cevModuleMDSType 4 }

-- DS-X9032   - MDS 9500 32-port 1/2Gbps FC Module

cevMDSDsX9032Smv  OBJECT IDENTIFIER
    ::= { cevModuleMDSType 5 }

-- DS-X9032-SMV  - MDS 9500 32-port Advanced Services Module (ASM)

cevMDSDsX9308Smip  OBJECT IDENTIFIER
    ::= { cevModuleMDSType 6 }

-- DS-X9308-SMIP - MDS 9500 8-port 1GE IP Storage Services Module

cevMDSDsX9560Smc  OBJECT IDENTIFIER
    ::= { cevModuleMDSType 7 }

-- DS-X9560-SMC - MDS  Caching Services Module (CSM)

cevMDSDsSfpFc2Gsw  OBJECT IDENTIFIER
    ::= { cevModuleMDSType 8 }

-- DS-SFP-FC-2G-SW  - 1/2 Gbps Fibre Channel-SW Small Form-Factor Pluggable, LC

cevMDSDsSfpFc2Glw  OBJECT IDENTIFIER
    ::= { cevModuleMDSType 9 }

-- DS-SFP-FC-2G-LW   - 1/2 Gbps Fibre Channel-LW Small Form-Factor Pluggable, LC

cevMDSDsSfpGeSw  OBJECT IDENTIFIER
    ::= { cevModuleMDSType 10 }

-- DS-SFP-GE-SW      -  1 Gbps Ethernet-SW Small Form-Factor Pluggable, LC

cevMDSDsSfpGeLw  OBJECT IDENTIFIER
    ::= { cevModuleMDSType 11 }

-- DS-SFP-GE-LW      -  1 Gbps Ethernet-LW Small Form-Factor Pluggable, LC

cevMDSDsC9500Cl  OBJECT IDENTIFIER
    ::= { cevModuleMDSType 12 }

-- DS-C9500-CL         - MDS 9500 Backplane Clock Module

cevMDSDsX9216K9Sup  OBJECT IDENTIFIER
    ::= { cevModuleMDSType 13 }

-- DS-X9216-K9-SUP  -  MDS 9216 16-port 1/2Gbps FC Module

cevMDSMemFld512M  OBJECT IDENTIFIER
    ::= { cevModuleMDSType 14 }

-- MEM-MDS-FLD512M   -  MDS 9500 Sup Compact Flash Disk, 512MB

cevMDSMemMd1G  OBJECT IDENTIFIER
    ::= { cevModuleMDSType 15 }

-- MEM-MDS-MD1G        -  MDS 9500 Sup Microdrive 1GB

cevMDSDsC9509Cl  OBJECT IDENTIFIER
    ::= { cevModuleMDSType 16 }

-- DS-C9509-CL   - MDS 9509 Clock Module

cevMDSDsC9506Cl  OBJECT IDENTIFIER
    ::= { cevModuleMDSType 17 }

-- DS-C9506-CL   - MDS 9506 Clock Module

cevMDSDsX9140K9Sup  OBJECT IDENTIFIER
    ::= { cevModuleMDSType 18 }

-- DS-X9140-K9-SUP  - MDS 9140 40-port 1/2 Gbps FC Module

cevMDSDsX9120K9Sup  OBJECT IDENTIFIER
    ::= { cevModuleMDSType 19 }

-- DS-X9120-K9-SUP  - MDS 9120 20-port 1/2 Gbps FC Module

cevMDSDsX9032Sma  OBJECT IDENTIFIER
    ::= { cevModuleMDSType 20 }

-- DS-X9032-SMA  - MDS Storage Services Module (SSM)

cevMDSDsX9216Mgt  OBJECT IDENTIFIER
    ::= { cevModuleMDSType 21 }

-- DS-X9216-MGT  - MDS 9216 SAM Module

cevMDSDsX930214K9  OBJECT IDENTIFIER
    ::= { cevModuleMDSType 22 }

-- DS-X9302-14K9 - 14FC+2GE Multiprotocol Services Module

cevMDSDsX9202  OBJECT IDENTIFIER
    ::= { cevModuleMDSType 23 }

-- DS-X9202 - 2x10G FC 10G FC Module

cevMDSDsX9304Smip  OBJECT IDENTIFIER
    ::= { cevModuleMDSType 24 }

-- DS-X9304-SMIP - MDS 4-port GE iSCSI/FCIP Services Module

cevMDSDsX9132K9Sup  OBJECT IDENTIFIER
    ::= { cevModuleMDSType 25 }

-- 32 FC-port hybrid supervisor module

cevMDSDsX9116K9Sup  OBJECT IDENTIFIER
    ::= { cevModuleMDSType 26 }

-- 16 FC-port hybrid supervisor module

cevMDSDsX9216IK9Sup  OBJECT IDENTIFIER
    ::= { cevModuleMDSType 27 }

-- DS-X9216I-K9-SUP 16 port hybrid (14FC +2 IP)supervisor

cevMDSDsX9530Sf2K9  OBJECT IDENTIFIER
    ::= { cevModuleMDSType 28 }

-- DS-X9530-SF2-K9  - Sup-2, Supervisor/Fabric module

cevMDSDsX9112  OBJECT IDENTIFIER
    ::= { cevModuleMDSType 29 }

-- DS-X9112-  12-port Fibre Channel switching module

cevMDSDsX9124  OBJECT IDENTIFIER
    ::= { cevModuleMDSType 30 }

-- DS-X9124-  24-port Fibre Channel switching module

cevMDSDsX9148  OBJECT IDENTIFIER
    ::= { cevModuleMDSType 31 }

-- DS-X9148-  48-port Fibre Channel switching module

cevMDSDsX9704  OBJECT IDENTIFIER
    ::= { cevModuleMDSType 32 }

-- DS-X9704-  4-port Fibre Channel switching module

cevMDSDs13SltFab1  OBJECT IDENTIFIER
    ::= { cevModuleMDSType 33 }

-- Cisco MDS 9513 Fabric 1 module

cevMDSDsC9513Cl  OBJECT IDENTIFIER
    ::= { cevModuleMDSType 34 }

-- Cisco MDS 9513 clock module - DS-C9513-CL

cevMDSDsX9124S2K9  OBJECT IDENTIFIER
    ::= { cevModuleMDSType 35 }

-- 24-port 1/2/4 Gig Supervisor Fabric Switch

cevMDSDsIBMFC  OBJECT IDENTIFIER
    ::= { cevModuleMDSType 36 }

-- Cisco 4Gb Fibre Channel Switch Module for IBM BladeCenter

cevMDSDsHPFC  OBJECT IDENTIFIER
    ::= { cevModuleMDSType 37 }

-- Fibre Channel Switch Module for HP BladeSystem

cevMDSDsX9222iK9Sup  OBJECT IDENTIFIER
    ::= { cevModuleMDSType 38 }

-- DS-X9222i-K9 coco supervisor

cevMDSDxX930418K9  OBJECT IDENTIFIER
    ::= { cevModuleMDSType 39 }

-- DS-X9304-18K9 coco Linecard

cevMDSDsX9134S2K9  OBJECT IDENTIFIER
    ::= { cevModuleMDSType 40 }

-- 32-port 1/2/4 with 10 Gig Supervisor Fabric Switch

cevMdsDSC9222iK9Sup  OBJECT IDENTIFIER
    ::= { cevModuleMDSType 41 }

-- Supervisor module in slot 1 of MDS 9222i chassis

cevMDSDsX9248FC48Gbps  OBJECT IDENTIFIER
    ::= { cevModuleMDSType 42 }

-- 48 port 1/2/4/8G 48Gbps FibreChannel linecard A-Oahu PID:DS-X9248-48

cevMDSDsX9248FC96Gbps  OBJECT IDENTIFIER
    ::= { cevModuleMDSType 43 }

-- 48 port 1/2/4/8G 96Gbps FibreChannel linecard TwinPeaks PID:DS-X9248-96

cevMDSDsX9316SSM  OBJECT IDENTIFIER
    ::= { cevModuleMDSType 44 }

-- Lanai PID=DS-X9316-SSM, 16 GE port Storage Service Module

cevMDSDs13SltFab2  OBJECT IDENTIFIER
    ::= { cevModuleMDSType 45 }

-- Cisco MDS 9513 Fabric2 (evia2)DS-13SLT-FAB2

cevMDSDsX922496k9  OBJECT IDENTIFIER
    ::= { cevModuleMDSType 46 }

-- 24 port singlepeak PID:DS-X9224-96K9

cevMDSDsX9716K9  OBJECT IDENTIFIER
    ::= { cevModuleMDSType 52 }

-- Midas  DS-X9716-K9 10-Gbps 16-Port ethernet-port FCoE Module

cevMDSDsX9248x256K9  OBJECT IDENTIFIER
    ::= { cevModuleMDSType 53 }

-- Zelda DS-X9248-256K9  48-Port 1/2/4/8/10Gbps FC Switching Module

cevMDSDsX9232x256K9  OBJECT IDENTIFIER
    ::= { cevModuleMDSType 54 }

-- Link DS-X9232-256K9  32-Port 1/2/4/8/10Gbps FC Switching Module

cevMDSDs13SlotFabricEvia3  OBJECT IDENTIFIER
    ::= { cevModuleMDSType 55 }

-- Evia3 DS-13SLT-FAB3  MDS9513 xbar 256Gbps Fabric Module3

cevMDSDsX9530Sf2AK9  OBJECT IDENTIFIER
    ::= { cevModuleMDSType 56 }

-- 2nd gen sup2a DS-X9530-SF2A-K9 for MDS

cevMDSDs9708HPK9  OBJECT IDENTIFIER
    ::= { cevModuleMDSType 57 }

-- DS-9708-HPK9  HP-Mira-midas

cevMDSDs9708K9  OBJECT IDENTIFIER
    ::= { cevModuleMDSType 58 }

-- DS-9708-K9 Mira-midas

cevMDSDSX9448n768K9  OBJECT IDENTIFIER
    ::= { cevModuleMDSType 61 }

-- DS-X9448-768K9, 48 Port 16 GBit/s Fiber Channel Linecard for MDS 10-Slot Director Switch, DS9710

cevMDSDSX9848n480K9SM  OBJECT IDENTIFIER
    ::= { cevModuleMDSType 62 }

-- DS-X9848-480-K9, 10G FCoE Storage Module for MDS 10-Slot Director Switch, DS9710

cevMDSDSX97SF1K9SUP  OBJECT IDENTIFIER
    ::= { cevModuleMDSType 63 }

-- DS-X97-SF1-K9, Supervisor Module for MDS 10-Slot Director Switch, DS9710

cevMDSDSX9710FAB1  OBJECT IDENTIFIER
    ::= { cevModuleMDSType 64 }

-- DS-X9710-FAB1, Fabric Module for MDS 10-Slot Director Switch, DS9710

cevMDS9710FCS  OBJECT IDENTIFIER
    ::= { cevModuleMDSType 65 }

-- MDS 9710 10 Slot Director switch chassis

cevMDS9250iIFSPS  OBJECT IDENTIFIER
    ::= { cevModuleMDSType 66 }

-- MDS 9250 Multiprotocol Fabric Switch, with support for FC, FCoE and FC-IP Protocols

cevMDS9250iIFSDC  OBJECT IDENTIFIER
    ::= { cevModuleMDSType 67 }

-- Daughter card for MDS 9250i Intelligent Fabric Switch

cevMDSDSC9250i22PK9SUPFS  OBJECT IDENTIFIER
    ::= { cevModuleMDSType 68 }

-- DS-C9250i-22PK9-SUP, Supervisor module for MDS 9250i Intelligent Fabric Switch

cevMDSDSX9848480K9  OBJECT IDENTIFIER
    ::= { cevModuleMDSType 69 }

-- DS-X9848-480K9, 48 port 1/10 Gbps FCoE module for M9700 platform

cevMDSDSX9706FAB1  OBJECT IDENTIFIER
    ::= { cevModuleMDSType 70 }

-- DS-X9706-FAB1, Fabric Module for MDS 6-Slot Director Switch

cevMDSDSC9148SK9SUP  OBJECT IDENTIFIER
    ::= { cevModuleMDSType 71 }

-- Supervisor module for MDS 9148 16G Fabric Switch

cevModuleC3220Type  OBJECT IDENTIFIER
    ::= { cevModule 54 }

-- Represents the base class for all the modules used in c3220.

cevC3220Smic  OBJECT IDENTIFIER
    ::= { cevModuleC3220Type 1 }

-- Serial Mobile Interface Card(SMIC) for the C3220 Mobile Access Router with 2 Serial Interfaces.

cevC3220Fesmic  OBJECT IDENTIFIER
    ::= { cevModuleC3220Type 2 }

-- Fast Ethernet Switch Mobile Interface Card(FESMIC) for the C3220 Mobile Access Router with 2 Fast Ethernet Interfaces.

cevModuleCrs1Type  OBJECT IDENTIFIER
    ::= { cevModule 55 }

-- Represents the base class for all the modules used in Crs1.

cevModuleCrs1RP  OBJECT IDENTIFIER
    ::= { cevModuleCrs1Type 1 }

-- Cisco CRS1 RP card.

cevModuleCrs1DRP  OBJECT IDENTIFIER
    ::= { cevModuleCrs1Type 2 }

-- Cisco CRS1 DRP Card.

cevModuleCrs18sS123Fabric  OBJECT IDENTIFIER
    ::= { cevModuleCrs1Type 3 }

-- S123 Fabric Card with 2 S1, 2 S2 & 2S3 ASICs, for CRS1 8 slots single chassis router

cevModuleCrs116sS123Fabric  OBJECT IDENTIFIER
    ::= { cevModuleCrs1Type 4 }

-- Cisco CRS1 S123 Fabric Card, for CRS1 16 slots single chassis router

cevModuleCrs116dS123TFabric  OBJECT IDENTIFIER
    ::= { cevModuleCrs1Type 5 }

-- Cisco CRS1 S123T Fabric Card, for CRS1 16 slots dual chassis router

cevModuleCrs116mS13Fabric  OBJECT IDENTIFIER
    ::= { cevModuleCrs1Type 6 }

-- Cisco CRS1 S13 Fabric Card, for CRS1 16 slots multi chassis router

cevModuleCrs116mS2CCFabric  OBJECT IDENTIFIER
    ::= { cevModuleCrs1Type 7 }

-- Cisco CRS1 S2CC Fabric Card, for CRS1 16 slots multi chassis router

cevModuleCrs116mS2Fabric  OBJECT IDENTIFIER
    ::= { cevModuleCrs1Type 8 }

-- Cisco CRS1 S2 Fabric Card, for CRS1 16 slots multi chassis router

cevModuleCrs1FanCtrllrLC  OBJECT IDENTIFIER
    ::= { cevModuleCrs1Type 9 }

-- Cisco CRS1 Line Card rack Fan Controller.

cevModuleCrs116mS2FanCtrllrFabric  OBJECT IDENTIFIER
    ::= { cevModuleCrs1Type 10 }

-- Cisco CRS1 Fabric rack Fan Controller, for CRS1 16 slots multi chassis router

cevModuleCrs1Alarm  OBJECT IDENTIFIER
    ::= { cevModuleCrs1Type 11 }

-- Cisco Crs1 Alarm Card.

cevModuleCrs116mFabricLED  OBJECT IDENTIFIER
    ::= { cevModuleCrs1Type 12 }

-- Cisco CRS1 S2 Fabric LED card, for CRS1 16 slots multi chassis router

cevModuleCrs1DRPPlim  OBJECT IDENTIFIER
    ::= { cevModuleCrs1Type 13 }

-- Cisco CRS1 DRP PLIM card.

cevModuleCrs116OC48Plim  OBJECT IDENTIFIER
    ::= { cevModuleCrs1Type 14 }

-- Cisco CRS1 16 port SONET OC-48 PLIM card.

cevModuleCrs14OC192VSRPlim  OBJECT IDENTIFIER
    ::= { cevModuleCrs1Type 15 }

-- Cisco CRS1 4 port SONET OC-192 VSR PLIM card

cevModuleCrs14OC192SRPlim  OBJECT IDENTIFIER
    ::= { cevModuleCrs1Type 16 }

-- Cisco CRS1 4 port SONET OC-192 SR PLIM card.

cevModulecrs14OC192LRPlim  OBJECT IDENTIFIER
    ::= { cevModuleCrs1Type 17 }

-- Cisco CRS1 4 port SONET OC-192 LR PLIM card.

cevModuleCrs1OC768VSRPlim  OBJECT IDENTIFIER
    ::= { cevModuleCrs1Type 18 }

-- Cisco CRS1 single port SONET OC-768 VSR PLIM card.

cevModuleCrs1OC768SRPlim  OBJECT IDENTIFIER
    ::= { cevModuleCrs1Type 19 }

-- Cisco CRS1 single port SONET OC-768 SR PLIM card.

cevModuleCrs16x10GePlim  OBJECT IDENTIFIER
    ::= { cevModuleCrs1Type 20 }

-- Cisco CRS1 6 port 10 Gigabit Ethernet PLIM card.

cevModuleCrs18x10GePlim  OBJECT IDENTIFIER
    ::= { cevModuleCrs1Type 21 }

-- Cisco CRS1 8 port 10 Gigabit Ethernet PLIM card.

cevModuleCrs18RP  OBJECT IDENTIFIER
    ::= { cevModuleCrs1Type 22 }

-- Cisco CRS-1 Series 8 Slots Route Processor

cevModuleCrs18Fabric  OBJECT IDENTIFIER
    ::= { cevModuleCrs1Type 23 }

-- Cisco CRS-1 Series 8 Slots Fabric Card (single)

cevModuleCrs1FabricShelfController  OBJECT IDENTIFIER
    ::= { cevModuleCrs1Type 24 }

-- Cisco CRS-1 Series Fabric Card Chassis Shelf Controller

cevModuleCrs1FabricSwitchFabric  OBJECT IDENTIFIER
    ::= { cevModuleCrs1Type 25 }

-- Cisco CRS-1 Series Fabric Card Chassis Switch Fabric card (s2)

cevModuleCrs1FabricLEDModule  OBJECT IDENTIFIER
    ::= { cevModuleCrs1Type 26 }

-- Cisco CRS-1 Series Fabric Card Chassis LED Module card

cevModuleCrs1FabricOIMSingleSlot  OBJECT IDENTIFIER
    ::= { cevModuleCrs1Type 27 }

-- Cisco CRS-1 Series Fabric Card Chassis Single Slot Optical Interface Module

cevModuleCrs1FabricOIMDualSlot  OBJECT IDENTIFIER
    ::= { cevModuleCrs1Type 28 }

-- Cisco CRS-1 Series Fabric Card Chassis Dual Slot Optical Interface Module

cevModuleCrs18dS123Fabric  OBJECT IDENTIFIER
    ::= { cevModuleCrs1Type 29 }

-- Cisco CRS-1 Series 8 Slots Fabric Card/Dual

cevModuleCrs18mS123Fabric  OBJECT IDENTIFIER
    ::= { cevModuleCrs1Type 30 }

-- Cisco CRS-1 Series 8 Slots Fabric Card/Multi

cevModuleCrs116dS123Fabric  OBJECT IDENTIFIER
    ::= { cevModuleCrs1Type 31 }

-- Cisco CRS-1 Series 16 Slots Fabric Card/Dual

cevModuleCrs1FccSc22Ge  OBJECT IDENTIFIER
    ::= { cevModuleCrs1Type 32 }

-- CRS-1 Fabric Chassis Integrated Switch Controller Card

cevModuleCrs1FccSFEc  OBJECT IDENTIFIER
    ::= { cevModuleCrs1Type 33 }

-- Cisco CRS-1 Series FC Chassis Shelf/Fan/Enet Controller

cevModuleCrs14x10GeCDwdmPlim  OBJECT IDENTIFIER
    ::= { cevModuleCrs1Type 34 }

-- Cisco CRS-1 4 port 10GE (C-band) DWDM PLIM

cevModuleCrs14OC192CDwdmPlim  OBJECT IDENTIFIER
    ::= { cevModuleCrs1Type 35 }

-- Cisco CRS-1 4 port OC192 (C-band) DWDM PLIM

cevModuleCrs1OC768CDwdmPlim  OBJECT IDENTIFIER
    ::= { cevModuleCrs1Type 36 }

-- Cisco CRS-1 OC768 (C-band) DWDM PLIM

cevModuleCrs1DRPBPlim  OBJECT IDENTIFIER
    ::= { cevModuleCrs1Type 37 }

-- Cisco CRS-1 Series Distributed Route Processor PLIM revision B

cevModuleCrs1DRPB  OBJECT IDENTIFIER
    ::= { cevModuleCrs1Type 38 }

-- Cisco CRS-1 Series Distributed Route Processor CPU board revision B

cevModuleCrs1OC768CDwdmDpskC  OBJECT IDENTIFIER
    ::= { cevModuleCrs1Type 39 }

-- Cisco CRS-1 OC768 DPSK C-BAND STD CHAN PLIM

cevModuleCrs14FabricCard  OBJECT IDENTIFIER
    ::= { cevModuleCrs1Type 42 }

-- Cisco CRS-1 Series 4 Slots Fabric Card

cevModuleCrsASPLIM  OBJECT IDENTIFIER
    ::= { cevModuleCrs1Type 43 }

-- Cisco CRS-1 Carrier Grade Service Engine PLIM

cevModuleCrs4OC192DptLr  OBJECT IDENTIFIER
    ::= { cevModuleCrs1Type 44 }

-- Cisco CRS-1 4xOC-192/STM-64 DPT Interface Module/LR

cevModuleCrs4OC192DptSr  OBJECT IDENTIFIER
    ::= { cevModuleCrs1Type 45 }

-- Cisco CRS-1 4xOC-192/STM-64 DPT Interface Module/SR

cevModuleCrs4OC192DptVs  OBJECT IDENTIFIER
    ::= { cevModuleCrs1Type 46 }

-- Cisco CRS-1 4xOC-192/STM-64 DPT Interface Module/VSR

cevModuleCrs14x10GE  OBJECT IDENTIFIER
    ::= { cevModuleCrs1Type 47 }

-- Cisco CRS-1 Series 4x10GE Interface Module

cevModuleCrs142x1GE  OBJECT IDENTIFIER
    ::= { cevModuleCrs1Type 48 }

-- Cisco CRS-1 Series 42x1GE Interface Module

cevModuleCrs120x1GeFl  OBJECT IDENTIFIER
    ::= { cevModuleCrs1Type 49 }

-- Cisco CRS-1 Series 20x1GE Flexible Interface Module

cevModuleCrs12x10GeFl  OBJECT IDENTIFIER
    ::= { cevModuleCrs1Type 50 }

-- Cisco CRS-1 Series 2x10GE WAN/LAN Flexible Interface Module

cevModuleCrs116Alarm  OBJECT IDENTIFIER
    ::= { cevModuleCrs1Type 51 }

-- Cisco CRS-1 Series 16 Slots Modular Power System Alarm Board

cevModuleCrs14x10GbeWLXfpPlim  OBJECT IDENTIFIER
    ::= { cevModuleCrs1Type 52 }

-- Cisco CRS-1 Series 4xGbE WAN/LAN XFP Interface Module

cevModuleCrs18x10GbeWLXfpPlim  OBJECT IDENTIFIER
    ::= { cevModuleCrs1Type 53 }

-- Cisco CRS-1 Series 8xGbE WAN/LAN XFP Interface Module

cevModuleCrs1LcB40G  OBJECT IDENTIFIER
    ::= { cevModuleCrs1Type 54 }

-- Cisco CRS-1 Series Modular Services Card revision B

cevModuleCrs1Lc40G  OBJECT IDENTIFIER
    ::= { cevModuleCrs1Type 55 }

-- Cisco CRS-1 Series Modular Services Card

cevModuleCrs114X10GBEWLXFPPlim  OBJECT IDENTIFIER
    ::= { cevModuleCrs1Type 56 }

-- Cisco CRS Series 14x10GbE LAN/WAN-PHY Interface Module

cevModuleCrs120X10GBEWLXFPPlim  OBJECT IDENTIFIER
    ::= { cevModuleCrs1Type 57 }

-- Cisco CRS Series 20x10GbE LAN/WAN-PHY Interface Module

cevModuleCrs11X100GBEPlim  OBJECT IDENTIFIER
    ::= { cevModuleCrs1Type 58 }

-- Cisco CRS Series 1x100GbE Interface Module

cevModuleCrs16FanCtB  OBJECT IDENTIFIER
    ::= { cevModuleCrs1Type 63 }

-- CRS-16-FAN-CT-B

cevModuleCrs16AlarmMB  OBJECT IDENTIFIER
    ::= { cevModuleCrs1Type 64 }

-- CRS Modular Power Alarm for CRS-16/S-B

cevModuleCrs16LccFCtB  OBJECT IDENTIFIER
    ::= { cevModuleCrs1Type 65 }

-- Cisco CRS-1 Fan Controller for 16 Slots LC Chassis Ver B

cevModuleCrs114X10GBEDwdmXfpPlim  OBJECT IDENTIFIER
    ::= { cevModuleCrs1Type 66 }

-- Cisco CRS-1 Series 14x10GbE DWDM Interface Module

cevModuleCrs120X10GBEDwdmXfpPlim  OBJECT IDENTIFIER
    ::= { cevModuleCrs1Type 67 }

-- Cisco CRS-1 Series 20x10GbE DWDM Interface Module

cevModuleCrs14X40GBEOtu3Plim  OBJECT IDENTIFIER
    ::= { cevModuleCrs1Type 68 }

-- Cisco CRS-1 Series 4x40GbE OTU3 Interface Module

cevModuleCrs11X100GBEDwdmPlim  OBJECT IDENTIFIER
    ::= { cevModuleCrs1Type 69 }

-- Cisco CRS-1 Series 1x100GbE DWDM Interface Module

cevModuleCrsCgsePlusPlim  OBJECT IDENTIFIER
    ::= { cevModuleCrs1Type 72 }

-- Cisco CRS-3 80 Gbps next generation Services PLIM

cevModuleCat35xxType  OBJECT IDENTIFIER
    ::= { cevModule 56 }

-- These are modules that are used in Catalyst 3500 switches

cevModuleCat356024PS  OBJECT IDENTIFIER
    ::= { cevModuleCat35xxType 1 }

-- 24 10/100 In-Line Power Ethernet ports + 2 Gigabit Ethernet SFP ports Layer 2/Layer 3 Module.(SFP Small Form factor Pluggable)

cevModuleCat356048PS  OBJECT IDENTIFIER
    ::= { cevModuleCat35xxType 2 }

-- 48 10/100 In-Line Power Ethernet ports + 4 Gigabit Ethernet SFP ports Layer 2/Layer 3 Module.(SFP Small Form factor Pluggable)

cevModuleCat3560G24PS  OBJECT IDENTIFIER
    ::= { cevModuleCat35xxType 3 }

-- Catalyst 3560 24 Power over Ethernet 10/100/1000 port + 4 Ethernet Gigabit SFP ports (SFP: Small Form factor Pluggable)

cevModuleCat3560G24TS  OBJECT IDENTIFIER
    ::= { cevModuleCat35xxType 4 }

-- Catalyst 3560 24 Ethernet 10/100/1000 port + 4 Ethernet Gigabit SFP ports (SFP: Small Form factor Pluggable)

cevModuleCat3560G48PS  OBJECT IDENTIFIER
    ::= { cevModuleCat35xxType 5 }

-- Catalyst 3560 48 Power over Ethernet 10/100/1000 port + 4 Ethernet Gigabit SFP ports (SFP: Small Form factor Pluggable)

cevModuleCat3560G48TS  OBJECT IDENTIFIER
    ::= { cevModuleCat35xxType 6 }

-- Catalyst 3560 48 Ethernet 10/100/1000 port + 4 Ethernet Gigabit SFP ports (SFP: Small Form factor Pluggable)

cevModuleCat356024TS  OBJECT IDENTIFIER
    ::= { cevModuleCat35xxType 7 }

-- Catalyst 3560 24 Ethernet 10/100 port + 2 Ethernet Gigabit SFP ports module. (SFP: Small Form factor Pluggable)

cevModuleCat356048TS  OBJECT IDENTIFIER
    ::= { cevModuleCat35xxType 8 }

-- Catalyst 3560 48 Ethernet 10/100 port + 4 Ethernet Gigabit SFP ports module. (SFP: Small Form factor Pluggable)

cevModuleCat3560E24TD  OBJECT IDENTIFIER
    ::= { cevModuleCat35xxType 9 }

-- Catalyst 3560E 24 10/100/1000 ports + 2 TenGigabit Ethernet (X2) ports

cevModuleCat3560E48TD  OBJECT IDENTIFIER
    ::= { cevModuleCat35xxType 10 }

-- Catalyst 3560E 48 10/100/1000 ports + 2 TenGigabit Ethernet (X2) ports

cevModuleCat3560E24PD  OBJECT IDENTIFIER
    ::= { cevModuleCat35xxType 11 }

-- Catalyst 3560E 24 10/100/1000 Power over Ethernet ports + 2 TenGigabit Ethernet (X2) ports

cevModuleCat3560E48PD  OBJECT IDENTIFIER
    ::= { cevModuleCat35xxType 12 }

-- Catalyst 3560E 48 10/100/1000 Power over Ethernet ports + 2 TenGigabit Ethernet (X2) ports

cevModuleCat35608PC  OBJECT IDENTIFIER
    ::= { cevModuleCat35xxType 13 }

-- Catalyst 3560 8 10/100 Power over Ethernet ports + 1 dual purpose Gigabit Ethernet ports

cevModuleCat3560e12d  OBJECT IDENTIFIER
    ::= { cevModuleCat35xxType 14 }

-- Catalyst 3560E 12 Ten GE (X2) ports

cevModuleCat3560E12SD  OBJECT IDENTIFIER
    ::= { cevModuleCat35xxType 15 }

-- Catalyst 3560E, 12 SFP Gigabit Ethernet ports + 2 TenGigabit Ethernet (X2) ports

cevModuleCat356012PCS  OBJECT IDENTIFIER
    ::= { cevModuleCat35xxType 16 }

-- Catalyst 3560 12 10/100 Power over Ethernet ports + 1 dual purpose Gigabit Ethernet port fixed configuration Layer 2 Ethernet switch

cevModuleCat3560v248ps  OBJECT IDENTIFIER
    ::= { cevModuleCat35xxType 17 }

-- 48 10/100 ports + 4 Ethernet Gigabit SFP ports fixed configuration Layer 2/Layer 3 Ethernet  Non-stackable PoE

cevModuleCat3560v248ts  OBJECT IDENTIFIER
    ::= { cevModuleCat35xxType 18 }

-- 48 10/100 ports + 4 Ethernet Gigabit SFP ports fixed configuration Layer 2/Layer 3 Ethernet  Non-stackable switch

cevModuleCat3560v224ps  OBJECT IDENTIFIER
    ::= { cevModuleCat35xxType 19 }

-- 24 10/100 ports + 2 Ethernet Gigabit SFP ports fixed configuration Layer 2/Layer 3 Ethernet  Non-stackable PoE switch

cevModuleCat3560v224ts  OBJECT IDENTIFIER
    ::= { cevModuleCat35xxType 20 }

-- 24 10/100 ports + 2 Ethernet Gigabit SFP ports fixed configuration Layer 2/Layer 3 Ethernet  Non-stackable switch

cevModuleCat3560v224tsD  OBJECT IDENTIFIER
    ::= { cevModuleCat35xxType 21 }

-- 24 10/100 ports + 2 Ethernet Gigabit SFP ports fixed configuration Layer 2/Layer 3 Ethernet  Non-stackable switch, DC power

cevModuleCat3560x24  OBJECT IDENTIFIER
    ::= { cevModuleCat35xxType 22 }

-- Catalyst 3560X 24 10/100/1000 Ports + 4 SFP Ports + 2 SFP+ Ports Layer 2/Layer 3 Ethernet Switch

cevModuleCat3560x48  OBJECT IDENTIFIER
    ::= { cevModuleCat35xxType 23 }

-- Catalyst 3560X 48 10/100/1000 Ports + 4 SFP Ports + 2 SFP+ Ports Layer 2/Layer 3 Ethernet Switch

cevModuleWsC3560CPD8ptS  OBJECT IDENTIFIER
    ::= { cevModuleCat35xxType 28 }

-- Catalyst 3560C 8 10/100/1000 with PoE and 2 Gig Copper PoE+ Uplinks fixed configuration Layer 2/Layer 3 Ethernet switch

cevModuleWsC3560C12pcS  OBJECT IDENTIFIER
    ::= { cevModuleCat35xxType 29 }

-- Catalyst 3560C 12 10/100 with PoE + 2 Gig Dual Media Uplinks fixed configuration Layer 2/Layer 3 Ethernet switch

cevModuleWsC3560C8pcS  OBJECT IDENTIFIER
    ::= { cevModuleCat35xxType 30 }

-- Catalyst 3560C 8 10/100 with PoE + 2 Gig Dual Media Uplinks fixed configuration Layer 2/Layer 3 Ethernet switch

cevModuleASA5523Type  OBJECT IDENTIFIER
    ::= { cevModule 57 }

cevMASA5523IsmSsmIds20K9  OBJECT IDENTIFIER
    ::= { cevModuleASA5523Type 1 }

-- Model 20 IDS Security Services Module for the ASA 5520 and 5530

cevMASA5523PmSsmIO4ge  OBJECT IDENTIFIER
    ::= { cevModuleASA5523Type 2 }

-- 4-port Gigabit Ethernet I/O Security Services Module for the ASA 5520 and 5530 (dual 1000BaseT/SFP GBIC ports, SFP GBICs not included)

cevMASA5523IsmSsmIds10K9  OBJECT IDENTIFIER
    ::= { cevModuleASA5523Type 3 }

-- Model 10 IDS Security Services Module for the ASA 5520 and 5530

cevPmSsmIO4geInc  OBJECT IDENTIFIER
    ::= { cevModuleASA5523Type 4 }

-- 4-port Gigabit Ethernet I/O Security Services Module for the ASA 5550 (dual 1000BaseT/SFP GBIC ports, SFP GBICs not included

cevMASA5523IsmSsmCsc10  OBJECT IDENTIFIER
    ::= { cevModuleASA5523Type 5 }

-- Model 10 CSC Security Services Module for the ASA 5500 Series Security Appliance

cevMASA5523IsmSsmCsc20  OBJECT IDENTIFIER
    ::= { cevModuleASA5523Type 6 }

-- Model 20 CSC Security Services Module for the ASA 5500 Series Security Appliance

cevMASA5523IsmSsmIds40K9  OBJECT IDENTIFIER
    ::= { cevModuleASA5523Type 7 }

-- Model 40 IDS Security Services Module for the ASA 5500 Series Security Appliance

cevModuleUmg9820Type  OBJECT IDENTIFIER
    ::= { cevModule 58 }

-- Umg9820 Gigabit Ethernet (processor Card) module

cevModuleUmg9820GigEProc  OBJECT IDENTIFIER
    ::= { cevModuleUmg9820Type 1 }

-- Umg9820 Gigabit Ethernet (processor Card) module

cevModuleUmg9820QamCard  OBJECT IDENTIFIER
    ::= { cevModuleUmg9820Type 2 }

-- Umg9820 Qam module

cevModuleONS15310Type  OBJECT IDENTIFIER
    ::= { cevModule 59 }

-- Cisco ONS 15310 platform

cevONS15310FeML100  OBJECT IDENTIFIER
    ::= { cevModuleONS15310Type 1 }

-- Cisco ONS 15310 Multi-Layer Fast Ethernet Card with 8 Front End Ports

cevONS15310FeCE100  OBJECT IDENTIFIER
    ::= { cevModuleONS15310Type 2 }

-- Cisco ONS 15310 Fast Ethernet Card with 8 Front End Ports

cevONS15310Ge8CE2  OBJECT IDENTIFIER
    ::= { cevModuleONS15310Type 3 }

-- Cisco ONS 15310 Gigabit Ethernet Card with 8 Front End Ports

cevModuleX2s  OBJECT IDENTIFIER
    ::= { cevModule 60 }

-- 10 Gigabit Pluggable X2 Modules

cevMX210GBaseSR  OBJECT IDENTIFIER
    ::= { cevModuleX2s 1 }

-- 10 Gigabit Ethernet X2 with Short Wave Multi Mode Fiber

cevMX210GBaseLR  OBJECT IDENTIFIER
    ::= { cevModuleX2s 2 }

-- 10 Gigabit Ethernet X2 with Long Wave Single Mode Fiber

cevMX210GBaseER  OBJECT IDENTIFIER
    ::= { cevModuleX2s 3 }

-- 10 Gigabit Ethernet X2 with Extra Long Wave Single Mode Fiber

cevMX210GBaseLX4  OBJECT IDENTIFIER
    ::= { cevModuleX2s 4 }

-- 10 Gigabit Ethernet X2 with Long Wave Multi Mode Fiber - 4 channels

cevMX210GBaseCX4  OBJECT IDENTIFIER
    ::= { cevModuleX2s 5 }

-- 10 Gigabit Ethernet X2 with Copper Wire

cevMX210GBaseZR  OBJECT IDENTIFIER
    ::= { cevModuleX2s 6 }

-- 10G Ethernet X2, 80km over Single Modle Fiber

cevMX210GBaseLW  OBJECT IDENTIFIER
    ::= { cevModuleX2s 7 }

-- 10G Ethernet X2, 1310nm WAN Serial Single Modle Fiber

cevMX210GBaseLRM  OBJECT IDENTIFIER
    ::= { cevModuleX2s 8 }

-- 10G Ethernet X2, 300m over 50um Muti Mode Fiber and 220m over FDDI grade Muti Mode Fiber

cevMX210GBaseT  OBJECT IDENTIFIER
    ::= { cevModuleX2s 9 }

-- 10G Ethernet X2, over twisted pair(Cat5E or Cat6) copper cabling

cevMX2s10GBaseWdmRxOnly  OBJECT IDENTIFIER
    ::= { cevModuleX2s 10 }

-- 10G Ethernet WDM Rx ONLY X2 Module

cevMX2s10GBaseDwdm3033  OBJECT IDENTIFIER
    ::= { cevModuleX2s 11 }

-- 10G Ethernet 3033 Laser X2 Module

cevMX2s10GBaseDwdm3112  OBJECT IDENTIFIER
    ::= { cevModuleX2s 13 }

-- 10G Ethernet 3112 Laser X2 Module

cevMX2s10GBaseDwdm3190  OBJECT IDENTIFIER
    ::= { cevModuleX2s 14 }

-- 10G Ethernet 3190 Laser X2 Module

cevMX2s10GBaseDwdm3268  OBJECT IDENTIFIER
    ::= { cevModuleX2s 15 }

-- 10G Ethernet 3268 Laser X2 Module

cevMX2s10GBaseDwdm3425  OBJECT IDENTIFIER
    ::= { cevModuleX2s 16 }

-- 10G Ethernet 3425 Laser X2 Module

cevMX2s10GBaseDwdm3504  OBJECT IDENTIFIER
    ::= { cevModuleX2s 17 }

-- 10G Ethernet 3504 Laser X2 Module

cevMX2s10GBaseDwdm3582  OBJECT IDENTIFIER
    ::= { cevModuleX2s 18 }

-- 10G Ethernet 3582 Laser X2 Module

cevMX2s10GBaseDwdm3661  OBJECT IDENTIFIER
    ::= { cevModuleX2s 19 }

-- 10G Ethernet 3661 Laser X2 Module

cevMX2s10GBaseDwdm3819  OBJECT IDENTIFIER
    ::= { cevModuleX2s 20 }

-- 10G Ethernet 3819 Laser X2 Module

cevMX2s10GBaseDwdm3898  OBJECT IDENTIFIER
    ::= { cevModuleX2s 21 }

-- 10G Ethernet 3898 Laser X2 Module

cevMX2s10GBaseDwdm3977  OBJECT IDENTIFIER
    ::= { cevModuleX2s 22 }

-- 10G Ethernet 3977 Laser X2 Module

cevMX2s10GBaseDwdm4056  OBJECT IDENTIFIER
    ::= { cevModuleX2s 23 }

-- 10G Ethernet 4056 Laser X2 Module

cevMX2s10GBaseDwdm4214  OBJECT IDENTIFIER
    ::= { cevModuleX2s 24 }

-- 10G Ethernet 4214 Laser X2 Module

cevMX2s10GBaseDwdm4294  OBJECT IDENTIFIER
    ::= { cevModuleX2s 25 }

-- 10G Ethernet 4294 Laser X2 Module

cevMX2s10GBaseDwdm4373  OBJECT IDENTIFIER
    ::= { cevModuleX2s 26 }

-- 10G Ethernet 4373 Laser X2 Module

cevMX2s10GBaseDwdm4453  OBJECT IDENTIFIER
    ::= { cevModuleX2s 27 }

-- 10G Ethernet 4453 Laser X2 Module

cevMX2s10GBaseDwdm4612  OBJECT IDENTIFIER
    ::= { cevModuleX2s 28 }

-- 10G Ethernet 4612 Laser X2 Module

cevMX2s10GBaseDwdm4692  OBJECT IDENTIFIER
    ::= { cevModuleX2s 29 }

-- 10G Ethernet 4692 Laser X2 Module

cevMX2s10GBaseDwdm4772  OBJECT IDENTIFIER
    ::= { cevModuleX2s 30 }

-- 10G Ethernet 4772 Laser X2 Module

cevMX2s10GBaseDwdm4851  OBJECT IDENTIFIER
    ::= { cevModuleX2s 31 }

-- 10G Ethernet 4851 Laser X2 Module

cevMX2s10GBaseDwdm5012  OBJECT IDENTIFIER
    ::= { cevModuleX2s 32 }

-- 10G Ethernet 5012 Laser X2 Module

cevMX2s10GBaseDwdm5092  OBJECT IDENTIFIER
    ::= { cevModuleX2s 33 }

-- 10G Ethernet 5092 Laser X2 Module

cevMX2s10GBaseDwdm5172  OBJECT IDENTIFIER
    ::= { cevModuleX2s 34 }

-- 10G Ethernet 5172 Laser X2 Module

cevMX2s10GBaseDwdm5252  OBJECT IDENTIFIER
    ::= { cevModuleX2s 35 }

-- 10G Ethernet 5252 Laser X2 Module

cevMX2s10GBaseDwdm5413  OBJECT IDENTIFIER
    ::= { cevModuleX2s 36 }

-- 10G Ethernet 5413 Laser X2 Module

cevMX2s10GBaseDwdm5494  OBJECT IDENTIFIER
    ::= { cevModuleX2s 37 }

-- 10G Ethernet 5494 Laser X2 Module

cevMX2s10GBaseDwdm5575  OBJECT IDENTIFIER
    ::= { cevModuleX2s 38 }

-- 10G Ethernet 5575 Laser X2 Module

cevMX2s10GBaseDwdm5655  OBJECT IDENTIFIER
    ::= { cevModuleX2s 39 }

-- 10G Ethernet 5655 Laser X2 Module

cevMX2s10GBaseDwdm5817  OBJECT IDENTIFIER
    ::= { cevModuleX2s 40 }

-- 10G Ethernet 5817 Laser X2 Module

cevMX2s10GBaseDwdm5898  OBJECT IDENTIFIER
    ::= { cevModuleX2s 41 }

-- 10G Ethernet 5898 Laser X2 Module

cevMX2s10GBaseDwdm5979  OBJECT IDENTIFIER
    ::= { cevModuleX2s 42 }

-- 10G Ethernet 5979 Laser X2 Module

cevMX2s10GBaseDwdm6061  OBJECT IDENTIFIER
    ::= { cevModuleX2s 43 }

-- 10G Ethernet 6061 Laser X2 Module

cevMX210GEBaseT  OBJECT IDENTIFIER
    ::= { cevModuleX2s 44 }

-- 10 Gigabit Ethernet X2 with four pairs of Class E or Class F balanced copper cabling

cevModuleCE5xxType  OBJECT IDENTIFIER
    ::= { cevModule 63 }

-- Represents the base class for all the modules used in cevModuleCE5xx

cevModuleCE50024TT  OBJECT IDENTIFIER
    ::= { cevModuleCE5xxType 1 }

-- Catalyst Express 500 24 10/100 ports + 2 Gigabit Ethernet ports module

cevModuleCE50024LC  OBJECT IDENTIFIER
    ::= { cevModuleCE5xxType 2 }

-- Catalyst Express 500 24 10/100 ports (4 Power Over Ethernet Ports) + 2 dual purpose Gigabit Ethernet ports module

cevModuleCE50024PC  OBJECT IDENTIFIER
    ::= { cevModuleCE5xxType 3 }

-- Catalyst Express 500 24 10/100 Power Over Ethernet Ports + 2 dual purpose Gigabit Ethernet ports module

cevModuleCE500G12TC  OBJECT IDENTIFIER
    ::= { cevModuleCE5xxType 4 }

-- Catalyst Express 500 8 Gigabit Ethernet Ports + 4 dual purpose Gigabit Ethernet ports module

cevModuleCE5208PC  OBJECT IDENTIFIER
    ::= { cevModuleCE5xxType 5 }

-- Catalyst Express 520 8 10/100 Power over Ethernet ports + 1 dual purpose Gigabit Ethernet port fixed configuration Layer 2 Ethernet switch

cevModuleCE52024PC  OBJECT IDENTIFIER
    ::= { cevModuleCE5xxType 6 }

-- Catalyst Express 520 24 Power Over Ethernet Ports + 2 dual purpose Gigabit Ethernet ports fixed configuration Layer 2 Ethernet switch

cevModuleCE52024TT  OBJECT IDENTIFIER
    ::= { cevModuleCE5xxType 7 }

-- Catalyst Express 520 24 10/100 ports + 2 Gigabit Ethernet ports fixed configuration Layer 2 Ethernet switch

cevModuleCE52024LC  OBJECT IDENTIFIER
    ::= { cevModuleCE5xxType 8 }

-- Catalyst Express 520 24 10/100 ports (4 Power Over Ethernet Ports) + 2 dual purpose Gigabit Ethernet ports fixed configuration Layer 2 Ethernet switch

cevModule520G24TC  OBJECT IDENTIFIER
    ::= { cevModuleCE5xxType 9 }

-- Catalyst Express 520 24 Gigabit Ethernet Ports + 2 dual purpose Gigabit Ethernet ports fixed configuration Layer 2 Ethernet switch

cevModuleMEType  OBJECT IDENTIFIER
    ::= { cevModule 64 }

-- Modules that are  used in Cisco Metro Ethernet Switches

cevModuleME240024TS  OBJECT IDENTIFIER
    ::= { cevModuleMEType 1 }

-- Metro Ethernet 2400 24 10/100 fast ethernet + 2 SFP ports module

cevModuleME340024TS  OBJECT IDENTIFIER
    ::= { cevModuleMEType 2 }

-- Metro Ethernet 3400 24 10/100 fast ethernet + 2 SFP ports module

cevModuleME3400G12CS  OBJECT IDENTIFIER
    ::= { cevModuleMEType 3 }

-- Metro Ethernet 3400, 12 GE/SFP ports + 4 SFP ports module

cevModuleME3400G2CS  OBJECT IDENTIFIER
    ::= { cevModuleMEType 4 }

-- Metro Ethernet 3400, 2 GE/SFP ports + 2 SFP ports module

cevModuleME492410GE  OBJECT IDENTIFIER
    ::= { cevModuleMEType 5 }

-- Metro Ethernet 492410GE, 24+4 GE/SFP ports + 2 X2 ports module.

cevModuleME340024FS  OBJECT IDENTIFIER
    ::= { cevModuleMEType 6 }

-- Metro Ethernet 3400 24 100BaseFX fast ethernet + 2 SFP ports module

cevModuleME3400E24TS  OBJECT IDENTIFIER
    ::= { cevModuleMEType 7 }

-- Metro Ethernet 3400E, 24 10/100 Fast Ethernet + 2 SFP ports module

cevModuleME3400EG12CS  OBJECT IDENTIFIER
    ::= { cevModuleMEType 8 }

-- Metro Ethernet 3400 , 12 GE/SFP ports + 4 SFP ports module

cevModuleME3400EG2CS  OBJECT IDENTIFIER
    ::= { cevModuleMEType 9 }

-- Metro Ethernet 3400E, 2 GE/SFP ports + 2 SFP ports module

cevModuleME3600X24FS  OBJECT IDENTIFIER
    ::= { cevModuleMEType 10 }

-- Cisco ME 3600X Ethernet Access Switch, 24 GE SFP ports + 2 10Gbps/1Gbps SFP+/SFP ports module

cevModuleME3600X24TS  OBJECT IDENTIFIER
    ::= { cevModuleMEType 11 }

-- Cisco ME 3600X Ethernet Access Switch, 24 10/100/1000 ports + 2 10Gbps/1Gbps SFP+/SFP ports module

cevModuleME3800X24FS  OBJECT IDENTIFIER
    ::= { cevModuleMEType 12 }

-- Cisco ME 3800X Carrier Ethernet Switch Router, 24 GE SFP ports + 2 10Gbps/1Gbps SFP+/SFP ports module

cevModuleCat4000EType  OBJECT IDENTIFIER
    ::= { cevModule 65 }

-- Group for the E-series product line (internally known as the K5 series)

cevCat4kWsx45Sup6e  OBJECT IDENTIFIER
    ::= { cevModuleCat4000EType 1 }

-- Catalyst 4500 E-Series Sup 6-E, 2x10GE(X2) w/TwinGig

cevCat4kWsx4648Rj45e  OBJECT IDENTIFIER
    ::= { cevModuleCat4000EType 2 }

-- Catalyst 4500 E-Series 48-Port 10/100/1000 (RJ45)

cevCat4kWsx4648Rj45ve  OBJECT IDENTIFIER
    ::= { cevModuleCat4000EType 3 }

-- Catalyst 4500 E-Series 48-Port PoE 802.3af 10/100/1000(RJ45)

cevCat4kWsx4606X2e  OBJECT IDENTIFIER
    ::= { cevModuleCat4000EType 4 }

-- Catalyst 4500 E-Series 6-Port 10GbE (X2)

cevCat4kWsx4624Sfpe  OBJECT IDENTIFIER
    ::= { cevModuleCat4000EType 5 }

-- Catalyst 4500 E-Series 24-Port GE (SFP)

cevCat4kWsx4590E  OBJECT IDENTIFIER
    ::= { cevModuleCat4000EType 7 }

-- Catalyst 4507R-E/4510R-E Fabric Redundancy Module

cevCat4kWsx4648Rj45je  OBJECT IDENTIFIER
    ::= { cevModuleCat4000EType 9 }

-- 48 Port 10/100/1000 Line Card with Jumbo Packet Support

cevCat4kWsx4648Rj45vPlusE  OBJECT IDENTIFIER
    ::= { cevModuleCat4000EType 10 }

-- 48 Port 10/100/1000 Preminum POE Line Card with Jumbo Frame Support

cevCat4kWsx45Sup6LE  OBJECT IDENTIFIER
    ::= { cevModuleCat4000EType 13 }

-- Catalyst 4500 E-Series Sup 6L-E, 2x10GE(X2)

cevCat4kWsx45Sup7e  OBJECT IDENTIFIER
    ::= { cevModuleCat4000EType 14 }

-- Catalyst 4500 EX-Series Sup 7-E, 4x10G SFP+

cevCat4kWsx4748Rj45VPlusE  OBJECT IDENTIFIER
    ::= { cevModuleCat4000EType 15 }

-- Catalyst 4500 EX-Series 48-Port PoE 802.3af 10/100/100(RJ45)

cevCat4kWsx4712SfpPlusE  OBJECT IDENTIFIER
    ::= { cevModuleCat4000EType 16 }

-- Catalyst 4500 EX-Series 12-Port 10G SFP+

cevCat4kWsx4612SfpE  OBJECT IDENTIFIER
    ::= { cevModuleCat4000EType 17 }

-- Catalyst 4500 E-Series 12-Port GE (SFP)

cevCat4kWsx4640CSfpE  OBJECT IDENTIFIER
    ::= { cevModuleCat4000EType 18 }

-- Catalyst 4500 EX-Series 40-Port SFP/80-Port C-SFP

cevCatWsX4748Rj45E  OBJECT IDENTIFIER
    ::= { cevModuleCat4000EType 19 }

-- 10/100/1000BaseT (RJ45) with 48 10/100/1000BaseT  Energy Efficient Ethernet (EEE) ports

cevCat4kWsX4748NgpoeE  OBJECT IDENTIFIER
    ::= { cevModuleCat4000EType 20 }

-- WS-X4748-UPOE+E is a RJ45-based 48 port linecard. The card supports UPOE, the Cisco-proprietary method of providing upto 60W of inline power per port

cevModuleN7KType  OBJECT IDENTIFIER
    ::= { cevModule 66 }

-- Group for the Nexus7000 N7K type of cards

cevN7KSup1  OBJECT IDENTIFIER
    ::= { cevModuleN7KType 1 }

-- supervisor1 module for Nexus7000 N7K

cevN7KM148GT04  OBJECT IDENTIFIER
    ::= { cevModuleN7KType 2 }

-- Nurburgring 48 port 10/100/1000 RJ-45 40G

cevN7KM132XP08  OBJECT IDENTIFIER
    ::= { cevModuleN7KType 3 }

-- AlbertPark 32 port 10GbE 80G

cevN7Kc7010Fab40  OBJECT IDENTIFIER
    ::= { cevModuleN7KType 4 }

-- Estoril10 40Gbps Fabric for Nexus7000 10 slot N7K

cevN7KM148GS11  OBJECT IDENTIFIER
    ::= { cevModuleN7KType 5 }

-- Jarama N7K-M148GS-11

cevN7Kc7018Fab1  OBJECT IDENTIFIER
    ::= { cevModuleN7KType 6 }

-- Estoril Fabric for Nexus7000 18 slot N7K-C7018-FAB-1

cevN7KF132Xp15  OBJECT IDENTIFIER
    ::= { cevModuleN7KType 7 }

-- Aida DCE N7K-F132XP-15 32 port 10G/1G SFP

cevN7KM108X212  OBJECT IDENTIFIER
    ::= { cevModuleN7KType 8 }

-- N7K-M108X2-12 Adelaide

cevN7KM108X212L  OBJECT IDENTIFIER
    ::= { cevModuleN7KType 9 }

-- N7K-M108X2-12L Adeliade-XL

cevN7KM148GS11L  OBJECT IDENTIFIER
    ::= { cevModuleN7KType 10 }

-- Jarama-XL N7K-M148GS-11L

cevN7KM116XP22L  OBJECT IDENTIFIER
    ::= { cevModuleN7KType 11 }

-- N7K-M116XP-22L  MotoGiro-16 16-Port 10Gb Ethernet Module with 160Gbps Fabric (requires SFP+ optic module)

cevN7KM108XP22L  OBJECT IDENTIFIER
    ::= { cevModuleN7KType 12 }

-- N7K-M108XP-22L  MotoGiro-8 8-Port 10Gb Ethernet Module with 80Gbps Fabric (requires SFP+ optic module)

cevN7KM132XP12L  OBJECT IDENTIFIER
    ::= { cevModuleN7KType 13 }

-- 10 Gbps Ethernet XL Module AlbertPark-XL N7K-M132XP-12L

cevN7Kc7009Fab2  OBJECT IDENTIFIER
    ::= { cevModuleN7KType 14 }

-- dijon9 N7K-C7009-FAB2 Fabric for Nexus7000 9slot boxster

cevN7Kc7010Fab2  OBJECT IDENTIFIER
    ::= { cevModuleN7KType 16 }

-- dijon10 N7K-C7010-FAB-2 Fabric for Nexus7000 10slot

cevN7Kc7018Fab2  OBJECT IDENTIFIER
    ::= { cevModuleN7KType 17 }

-- dijon18 N7K-C7018-FAB-2 Fabric for Nexus7000 18slot

cevN7KF248XP24  OBJECT IDENTIFIER
    ::= { cevModuleN7KType 18 }

-- 1/10 Gbps Ethernet Module N7K-F248XP-24

cevN7KF248XT24  OBJECT IDENTIFIER
    ::= { cevModuleN7KType 19 }

-- 1/10 Gbps BASE-T Ethernet Module N7K-F248XT-24

cevN7KSUP2  OBJECT IDENTIFIER
    ::= { cevModuleN7KType 20 }

-- Nexus 7000 Supervisor Module N7K-SUP2

cevN7KM202CF22L  OBJECT IDENTIFIER
    ::= { cevModuleN7KType 21 }

-- 10/40/100 Gbps Ethernet Module N7K-M202CF-22L

cevN7KM206FQ23L  OBJECT IDENTIFIER
    ::= { cevModuleN7KType 22 }

-- 10/40 Gbps Ethernet Module N7K-M206FQ-23L

cevN7KM148GT11L  OBJECT IDENTIFIER
    ::= { cevModuleN7KType 23 }

-- nurburing-XL N7K-M148GT-11L

cevN7KSMNAMK9  OBJECT IDENTIFIER
    ::= { cevModuleN7KType 27 }

-- N7K-SM-NAM-K9 Network Analysis Module for Nexus 7000

cevN7KFabricExtenderConnectionCable  OBJECT IDENTIFIER
    ::= { cevModuleN7KType 31 }

-- FEX Fabric Extender cabling

cevN7KM224XP23L  OBJECT IDENTIFIER
    ::= { cevModuleN7KType 32 }

-- autodromo10 24 port 10G ethernet nexus7000 N7K-M224XP-23L

cevN7KSUP2E  OBJECT IDENTIFIER
    ::= { cevModuleN7KType 33 }

-- silverstoneHeavy sup2e N7K-SUP2E

cevN7KForwardingEngine  OBJECT IDENTIFIER
    ::= { cevModuleN7KType 34 }

-- Forwarding engine asic on nexus n7k linecards

cevN7KF248XT25E  OBJECT IDENTIFIER
    ::= { cevModuleN7KType 45 }

-- N7K-F248XT-25E Enhanced 1/10 Gbps BASE-T Ethernet Module

cevN7KF248XP25E  OBJECT IDENTIFIER
    ::= { cevModuleN7KType 46 }

-- N7K-F248XP-25E Enhanced 1/10 Gbps Ethernet Module

cevModuleASA5580Type  OBJECT IDENTIFIER
    ::= { cevModule 67 }

-- Group for the ASA5580 Type of cards

cevModuleASA5580Pm4x1geCu  OBJECT IDENTIFIER
    ::= { cevModuleASA5580Type 1 }

-- ASA 5580 4 port GE Copper Interface Card

cevModuleASA5580Pm4x1geFi  OBJECT IDENTIFIER
    ::= { cevModuleASA5580Type 2 }

-- ASA 5580 4 port GE Fiber Interface Card

cevModuleASA5580Pm2x10geFi  OBJECT IDENTIFIER
    ::= { cevModuleASA5580Type 3 }

-- ASA 5580 2 port 10GE Fiber Interface Card

cevModuleASR1000Type  OBJECT IDENTIFIER
    ::= { cevModule 68 }

-- These are modules that are used in Cisco Aggregation Services Router 1000 Series

cevModuleASR1000RP1  OBJECT IDENTIFIER
    ::= { cevModuleASR1000Type 1 }

-- Cisco ASR1000 Routing Processor 1 Module

cevModuleASR1000ESP10  OBJECT IDENTIFIER
    ::= { cevModuleASR1000Type 2 }

-- Cisco ASR1000 Embedded Services Processor 10Gbps Module

cevModuleASR1000SIP10  OBJECT IDENTIFIER
    ::= { cevModuleASR1000Type 3 }

-- Cisco ASR1000 SPA Interface Processor 10 Module

cevModuleASR1000UnknownRP  OBJECT IDENTIFIER
    ::= { cevModuleASR1000Type 4 }

-- Cisco ASR1000 Unknown Routing Processor

cevModuleASR1000UnknownESP  OBJECT IDENTIFIER
    ::= { cevModuleASR1000Type 5 }

-- Cisco ASR1000 Unknown Embedded Services Processor

cevModuleASR1000UnknownSIP  OBJECT IDENTIFIER
    ::= { cevModuleASR1000Type 6 }

-- Cisco ASR1000 Unknown SPA Interface Processor

cevModuleASR1002RP1  OBJECT IDENTIFIER
    ::= { cevModuleASR1000Type 7 }

-- Cisco ASR1002 Routing Processor 1 Module

cevModuleASR1000ESP5  OBJECT IDENTIFIER
    ::= { cevModuleASR1000Type 8 }

-- Cisco ASR1000 Embedded Services Processor 5Gbps Module

cevModuleASR1000ESP20  OBJECT IDENTIFIER
    ::= { cevModuleASR1000Type 9 }

-- Cisco ASR1000 Embedded Services Processor 20Gbps Module

cevModuleASR1002Spa4pGe  OBJECT IDENTIFIER
    ::= { cevModuleASR1000Type 10 }

-- 4 port Ge SPA Build-In Module for Cisco ASR1002

cevModuleASR1002SIP10  OBJECT IDENTIFIER
    ::= { cevModuleASR1000Type 11 }

-- Cisco ASR1002 SPA Interface Processor 10 Module

cevModuleASR1000SIP40  OBJECT IDENTIFIER
    ::= { cevModuleASR1000Type 12 }

-- Cisco ASR1000 SPA Interface Processor 40 Module

cevModuleASR1000RP2  OBJECT IDENTIFIER
    ::= { cevModuleASR1000Type 13 }

-- Cisco ASR1000 Routing Processor 2 Module

cevModuleASR1000ESP10N  OBJECT IDENTIFIER
    ::= { cevModuleASR1000Type 14 }

-- Cisco ASR1000 Embedded Services Processor 10Gbps Module without security feature

cevModuleASR1002FESP  OBJECT IDENTIFIER
    ::= { cevModuleASR1000Type 15 }

-- Cisco ASR1002F Embedded Services Processor 2.5Gbps Module

cevModuleASR1002FSIP10  OBJECT IDENTIFIER
    ::= { cevModuleASR1000Type 16 }

-- Cisco ASR1002F SPA Interface Processor 10 Module

cevModuleASR1000ESP40  OBJECT IDENTIFIER
    ::= { cevModuleASR1000Type 17 }

-- Cisco ASR1000 Embedded Services Processor 40Gbps Module

cevModuleASR1001RP  OBJECT IDENTIFIER
    ::= { cevModuleASR1000Type 18 }

-- Cisco ASR1001 Route Process

cevModuleASR1001ESP  OBJECT IDENTIFIER
    ::= { cevModuleASR1000Type 19 }

-- Cisco ASR1001 Embedded Services Processor

cevModuleASR1001SIP  OBJECT IDENTIFIER
    ::= { cevModuleASR1000Type 20 }

-- Cisco ASR1001 SPA Interface Processor

cevModuleASR1001Spa4pGe  OBJECT IDENTIFIER
    ::= { cevModuleASR1000Type 21 }

-- Built-in 4 port Ge SPA Module for Cisco

cevModuleASR1001IDC2xOc3Pos  OBJECT IDENTIFIER
    ::= { cevModuleASR1000Type 22 }

-- Cisco ASR1001 2xOc3Pos Integrated Daughter Card

cevModuleASR1001IDC4xT3  OBJECT IDENTIFIER
    ::= { cevModuleASR1000Type 23 }

-- Cisco ASR1001 2xOc3Pos Integrated Daughter Card

cevModuleASR1001IDC8xChT1E1  OBJECT IDENTIFIER
    ::= { cevModuleASR1000Type 24 }

-- Cisco ASR1002 8xChT1/E1 Integrated Daughter Card

cevModuleASR1001IDC4xGe  OBJECT IDENTIFIER
    ::= { cevModuleASR1000Type 25 }

-- Cisco ASR1001 4xGe Integrated Daughter Card

cevModuleASR1001IDCHDD  OBJECT IDENTIFIER
    ::= { cevModuleASR1000Type 26 }

-- ASR1001 harddisk Integrated Daughter Card

cevModuleASR1002XRP  OBJECT IDENTIFIER
    ::= { cevModuleASR1000Type 27 }

-- Cisco ASR1002-X Routing Processor Module

cevModuleASR1002XESP  OBJECT IDENTIFIER
    ::= { cevModuleASR1000Type 28 }

-- Cisco ASR1002-X Embedded Services Processor 2.5Gbps Module

cevModuleASR1002XSIP  OBJECT IDENTIFIER
    ::= { cevModuleASR1000Type 29 }

-- Cisco ASR1002-X SPA Interface Processor Module

cevModuleASR1002X6xGeBuiltIn  OBJECT IDENTIFIER
    ::= { cevModuleASR1000Type 30 }

-- Built-in 6 port Ge Module for Cisco ASR1002-X

cevModuleASR1000ESP100  OBJECT IDENTIFIER
    ::= { cevModuleASR1000Type 31 }

-- Cisco ASR1000 Embedded Services Processor 100Gbps Module

cevModuleASR1000ELC2xT20xGe  OBJECT IDENTIFIER
    ::= { cevModuleASR1000Type 33 }

-- Integrated Daughter Card  2xT+20xGE for Cisco ASR1000 Ethernet Line 40G Card. It contains 20-port GigabitEtherent ports and 2-port TenGigabitEtherent ports

cevModuleASR1000ELC40GModule  OBJECT IDENTIFIER
    ::= { cevModuleASR1000Type 34 }

-- This is a Cisco ASR1000 Ethernet Line Card of 40G capacity

cevModuleASR1002XCRP  OBJECT IDENTIFIER
    ::= { cevModuleASR1000Type 35 }

-- Cisco ASR1002-XC Routing Processor Module

cevModuleASR1002XCESP  OBJECT IDENTIFIER
    ::= { cevModuleASR1000Type 36 }

-- Cisco ASR1002-XC Embedded Services Processor Module

cevModuleASR1002XCSIP  OBJECT IDENTIFIER
    ::= { cevModuleASR1000Type 37 }

-- Cisco ASR1002-XC SPA Interface Processor Module

cevModuleASR1002XC2xGeBuiltIn  OBJECT IDENTIFIER
    ::= { cevModuleASR1000Type 38 }

-- Built-in 2 port Ge Module for Cisco ASR1002-X

cevModuleCatRfgwType  OBJECT IDENTIFIER
    ::= { cevModule 69 }

-- Cards that go into Rfgw chassis

cevRfgwDtcc  OBJECT IDENTIFIER
    ::= { cevModuleCatRfgwType 1 }

-- DOCSIS Timing, Communication, and Control Plus Card for RF gateway

cevRfgwQam48ABC  OBJECT IDENTIFIER
    ::= { cevModuleCatRfgwType 2 }

-- Card with 12 ports, each having 4 QAM (Quadrature Amplitude Modulation)channels, based on ITU-T J.83 Annex A, B & C

cevRfgwPort4Qam  OBJECT IDENTIFIER
    ::= { cevModuleCatRfgwType 3 }

-- QAM (Quadrature Amplitude Modulation) port with 4 channels each

cevRfgwRfswitch  OBJECT IDENTIFIER
    ::= { cevModuleCatRfgwType 4 }

-- RF switch card

cevRfgwQam384ABC  OBJECT IDENTIFIER
    ::= { cevModuleCatRfgwType 5 }

-- Card with 8 ports, each having 128 QAM channels, based on ITU-T J.83 Annex A, B & C

cevModuleVgdType  OBJECT IDENTIFIER
    ::= { cevModule 70 }

-- Group for VGD cards

cevVgdDfcCT3  OBJECT IDENTIFIER
    ::= { cevModuleVgdType 1 }

-- VGD Series Channelized T3 Interface Card

cevVgdDfcVFC  OBJECT IDENTIFIER
    ::= { cevModuleVgdType 2 }

-- VGD Series Voice Feature Card with Six Packet Voice Data Modules (PVDM2) module slots

cevVgdDfcCarrier  OBJECT IDENTIFIER
    ::= { cevModuleVgdType 3 }

-- Carrier Card that holds VGD Series Feature/Interface Cards

cevModuleIEType  OBJECT IDENTIFIER
    ::= { cevModule 71 }

-- new switch product line for IE

cevModuleIE30004TC  OBJECT IDENTIFIER
    ::= { cevModuleIEType 1 }

-- Cisco Industrial Ethernet Switch IE 3000 with 4 10/100 + 2 T/SFP Ethernet Interfaces

cevModuleIE30008TC  OBJECT IDENTIFIER
    ::= { cevModuleIEType 2 }

-- Cisco Industrial Ethernet Switch IE3000 with 8 10/100 + 2 T/SFP Ethernet Interfaces

cevModuleIE30008TM  OBJECT IDENTIFIER
    ::= { cevModuleIEType 3 }

-- Cisco Industrial Ethernet Switch Expansion Module IE3000, 8 10/100

cevModuleIE30008FM  OBJECT IDENTIFIER
    ::= { cevModuleIEType 4 }

-- Cisco Industrial Ethernet Switch Expansion Module IE3000, 8 100FX interfaces

cevModuleRAIE1783MS06T  OBJECT IDENTIFIER
    ::= { cevModuleIEType 5 }

-- Cisco-Rockwell Industrial Ethernet Switch 1783 with 4 10/100 + 2 T/SFP Ethernet Interfaces

cevModuleRAIE1783MS10T  OBJECT IDENTIFIER
    ::= { cevModuleIEType 6 }

-- Cisco Rockwell Industrial Ethernet Switch IE1783 with 8 10/100 + 2 T/SFP Ethernet Interfaces

cevModuleRAIE1783MX08T  OBJECT IDENTIFIER
    ::= { cevModuleIEType 7 }

-- Cisco-Rockwell Industrial Ethernet Switch Expansion Module IE1783 with 8 10/100 interface

cevModuleRAIE1783MX08F  OBJECT IDENTIFIER
    ::= { cevModuleIEType 8 }

-- Cisco-Rockwell Industrial Ethernet Switch Expansion Module IE1783 with 8 100FX interfaces

cevModuleIE301016S8PC  OBJECT IDENTIFIER
    ::= { cevModuleIEType 9 }

-- Cisco Industrial Ethernet 3010 Switch with 16 100 SFP + 8 10/100 + 2 T/SFP Ethernet Interfaces

cevModuleRAIE1783RMS06T  OBJECT IDENTIFIER
    ::= { cevModuleIEType 13 }

-- Cisco-Rockwell Industrial Ethernet Switch IE1783 with 4 10/100 + 2 T/SFP Ethernet Interfaces

cevModuleRAIE1783RMS10T  OBJECT IDENTIFIER
    ::= { cevModuleIEType 14 }

-- Cisco Rockwell Industrial Ethernet Switch IE1783 with 8 10/100 + 2 T/SFP Ethernet Interfaces

cevModuleIE200016TCGP  OBJECT IDENTIFIER
    ::= { cevModuleIEType 52 }

-- Cisco IA Base + Lite Industrial Ethernet 2000 Switch, 12 10/100 T + 2 1000 T/SFP + 4 POE

cevModuleIE200016TCGEP  OBJECT IDENTIFIER
    ::= { cevModuleIEType 53 }

-- Cisco IA Base + 1588 Industrial Ethernet 2000 Switch, 12 10/100 T + 2 1000 T/SFP + 4 POE

cevModuleIE200016TCGNXP  OBJECT IDENTIFIER
    ::= { cevModuleIEType 54 }

-- Cisco IA Base + 1588 + Conformal coating Industrial Ethernet 2000 Switch, 12 10/100 T + 2 1000 T/SFP + 4 POE

cevModuleIE30004SM  OBJECT IDENTIFIER
    ::= { cevModuleIEType 55 }

-- Cisco Industrial Ethernet Switch Expansion Module IE3000, 4 100FX interfaces

cevModuleIE30008SM  OBJECT IDENTIFIER
    ::= { cevModuleIEType 56 }

-- Cisco Industrial Ethernet Switch Expansion Module IE3000, 8 100FX interfaces

cevModuleRAIE1783MX04S  OBJECT IDENTIFIER
    ::= { cevModuleIEType 57 }

-- Cisco-Rockwell Industrial Ethernet Switch Expansion Module 1783, 4 100FX interfaces

cevModuleRAIE1783MX08S  OBJECT IDENTIFIER
    ::= { cevModuleIEType 58 }

-- Cisco-Rockwell Industrial Ethernet Switch Expansion Module 1783, 8 100FX interfaces

cevModuleIE30004PC  OBJECT IDENTIFIER
    ::= { cevModuleIEType 59 }

-- Cisco Industrial Ethernet Switch Expansion Module IE3000, 4 POE 10/100 interfaces

cevModuleIE30004PC4TC  OBJECT IDENTIFIER
    ::= { cevModuleIEType 60 }

-- Cisco Industrial Ethernet Switch Expansion Module IE3000, 4 POE and 4 nPOE 10/100 interfaces

cevModuleRAIE1783MX04E  OBJECT IDENTIFIER
    ::= { cevModuleIEType 61 }

-- Cisco-Rockwell Industrial Ethernet Switch Expansion Module 1783,  4 POE 10/100 interfaces

cevModuleRAIE1783MX04T04E  OBJECT IDENTIFIER
    ::= { cevModuleIEType 62 }

-- Cisco-Rockwell Industrial Ethernet Switch Expansion Module 1783, 4 POE and 4 nPOE 10/100 interfaces

cevModuleIE20008TCGN  OBJECT IDENTIFIER
    ::= { cevModuleIEType 63 }

-- Cisco IA Base + 1588 + NAT Industrial Ethernet 2000 Switch, 8 10/100 T + 2 1000 T/SFP

cevModuleIE200016TCGN  OBJECT IDENTIFIER
    ::= { cevModuleIEType 64 }

-- Cisco IA Base + 1588 + NAT Industrial Ethernet 2000 Switch, 16 10/100 T + 2 100 T + 2 1000 T/SFP

cevModuleRAIE1783BMS20CGN  OBJECT IDENTIFIER
    ::= { cevModuleIEType 65 }

-- Cisco Rockwell IA Base + 1588+NAT Industrial Ethernet 2000 Switch, 16 10/100 T + 2 100 T + 2 1000 T/SFP

cevModuleRAIE1783BMS12T4E2CGL  OBJECT IDENTIFIER
    ::= { cevModuleIEType 66 }

-- Rockwell IA Base + Lite Industrial Ethernet 2000 Switch, 12 10/100 T + 2 1000 T/SFP + 4 POE

cevModuleRAIE1783BMS12T4E2CGP  OBJECT IDENTIFIER
    ::= { cevModuleIEType 67 }

-- Rockwell IA Base + 1588 Industrial Ethernet 2000 Switch, 12 10/100 T + 2 1000 T/SFP + 4 POE

cevModuleRAIE1783BMS12T4E2CGNK  OBJECT IDENTIFIER
    ::= { cevModuleIEType 68 }

-- Rockwell IA Base + NAT + 1588 + Conformal Coating  Industrial Ethernet 2000 Switch, 12 10/100 T + 2 1000 T/SFP + 4 POE

cevModuleIem30004Pc  OBJECT IDENTIFIER
    ::= { cevModuleIEType 69 }

-- 4 POE port expansion module

cevModuleIem30004Pc4TC  OBJECT IDENTIFIER
    ::= { cevModuleIEType 70 }

-- 4 POE port 4 n-POE port expansion module

cevModule1783MX04E  OBJECT IDENTIFIER
    ::= { cevModuleIEType 71 }

-- 4 port POE expansion module

cevModule1783MX04T04E  OBJECT IDENTIFIER
    ::= { cevModuleIEType 72 }

-- 4 POE port 4 n-POE expansion module

cevModuleIE20008T67B  OBJECT IDENTIFIER
    ::= { cevModuleIEType 79 }

-- Cisco IE2000 IP67 Variant Switch with  8 port 10/100 downlink, LAN Base Image

cevModuleIE200016T67B  OBJECT IDENTIFIER
    ::= { cevModuleIEType 80 }

-- Cisco IE2000 IP67 Variant Switch with 16 port 10/100 downlink, LAN Base Image

cevModuleIE200024T67B  OBJECT IDENTIFIER
    ::= { cevModuleIEType 81 }

-- Cisco IE2000 IP67 Variant Switch with 24 port 10/100 downlink, LAN Base Image

cevModuleIE20008T67PGE  OBJECT IDENTIFIER
    ::= { cevModuleIEType 82 }

-- Cisco IE2000 IP67 Variant Switch with  4 port 10/100 downlink, 4-port POE /POE+, 2 10/100/1000 uplink, LAN Base Image, can support PTP, NAT

cevModuleIE200016T67PGE  OBJECT IDENTIFIER
    ::= { cevModuleIEType 83 }

-- Cisco IE2000 IP67 Variant Switch with  8 port 10/100 downlink, 8-port POE / 4-port POE+, 2 10/100/1000 uplink, LAN Base Image, can support PTP, NAT

cevModuleRAIE1783ZMS8TA  OBJECT IDENTIFIER
    ::= { cevModuleIEType 84 }

-- Rockwell IE2000 IP67 Variant Switch with  8 port 10/100 downlink, LAN Base Image

cevModuleRAIE1783ZMS16TA  OBJECT IDENTIFIER
    ::= { cevModuleIEType 85 }

-- Rockwell IE2000 IP67 Variant Switch with  16 port 10/100 downlink, LAN Base Image

cevModuleRAIE1783ZMS24TA  OBJECT IDENTIFIER
    ::= { cevModuleIEType 86 }

-- Rockwell IE2000 IP67 Variant Switch with  24 port 10/100 downlink, LAN Base Image

cevModuleRAIE1783ZMS4T4E2TGP  OBJECT IDENTIFIER
    ::= { cevModuleIEType 87 }

-- Rockwell IE2000 IP67 Variant Switch with 4 port 10/100 downlink, 4-port POE /POE+, 2 10/100/1000 uplink, LAN Base Image, can support PTP, NAT

cevModuleRAIE1783ZMS8T8E2TGP  OBJECT IDENTIFIER
    ::= { cevModuleIEType 88 }

-- Rockwell IE2000 IP67 Variant Switch with  8 port 10/100 downlink, 8-port POE / 4-port POE+, 2 10/100/1000 uplink, LAN Base Image, can support PTP, NAT

cevModuleN5KType  OBJECT IDENTIFIER
    ::= { cevModule 72 }

-- Group for the Nexus 5000 N5K Type of cards

cevN5kM1008  OBJECT IDENTIFIER
    ::= { cevModuleN5KType 1 }

-- Expansion Module, 8 port FC 1/2/4G (requires SFP)

cevN5KM1404  OBJECT IDENTIFIER
    ::= { cevModuleN5KType 2 }

-- Expansion Module, 4x10GE 4xFC 1/2/4G (requires SFP+/SFP)

cevN5kM1Blnk  OBJECT IDENTIFIER
    ::= { cevModuleN5KType 3 }

-- Expansion Module Blank

cevN5KM1600  OBJECT IDENTIFIER
    ::= { cevModuleN5KType 4 }

-- Expansion Module, 6 port 10GE (req SFP+)

cevN5kC5020FixedModule  OBJECT IDENTIFIER
    ::= { cevModuleN5KType 5 }

-- The fixed module that has 40 XE ports + supervisor

cevN5kC5010FixedModule  OBJECT IDENTIFIER
    ::= { cevModuleN5KType 6 }

-- The fixed module that has 20 XE ports + supervisor in Nexus 5010

cevN5kFabricExtenderConnection  OBJECT IDENTIFIER
    ::= { cevModuleN5KType 7 }

-- Fabric Extender cabling to N5K representation

cevN5kC5548pFixedModule  OBJECT IDENTIFIER
    ::= { cevModuleN5KType 10 }

-- The fixed module that has 32 XE ports + supervisor in Nexus

cevN5KN55M16P  OBJECT IDENTIFIER
    ::= { cevModuleN5KType 11 }

-- Expansion Module, 16x10GE (requires SFP)

cevN5KN55M8P8FP  OBJECT IDENTIFIER
    ::= { cevModuleN5KType 12 }

-- Expansion Module, 8x10GE + 8xFC 8G (requires SFP)

cevN5KN55M16UP  OBJECT IDENTIFIER
    ::= { cevModuleN5KType 13 }

-- Expansion Module, 16- Port Unified Port Module

cevN5KN55DL2  OBJECT IDENTIFIER
    ::= { cevModuleN5KType 14 }

-- Nexus 5548 Layer 2 IO Module

cevN5KN55D160L3  OBJECT IDENTIFIER
    ::= { cevModuleN5KType 15 }

-- Nexus 5548 Daughter Card with 160G Layer 3 connectivity

cevN5KN55M160L3  OBJECT IDENTIFIER
    ::= { cevModuleN5KType 16 }

-- Nexus 5596 Expansion module with 160G Layer 3 connectivity

cevN5KC5596UpFixedModule  OBJECT IDENTIFIER
    ::= { cevModuleN5KType 17 }

-- The fixed module that has 48 XE ports + supervisor in Nexus 5596

cevN5KN55M16FP  OBJECT IDENTIFIER
    ::= { cevModuleN5KType 18 }

-- Expansion Module, 16xFC 8G (requires SFP)

cevN5kC5548UPFixedModule  OBJECT IDENTIFIER
    ::= { cevModuleN5KType 19 }

-- The fixed module that has 32 Unified ports + supervisor in Nexus 5548

cevN5KN55M160L3V2  OBJECT IDENTIFIER
    ::= { cevModuleN5KType 20 }

-- Nexus 5596 Layer 3 Expansion Module, Version 2

cevN5KN55D160L3V2  OBJECT IDENTIFIER
    ::= { cevModuleN5KType 21 }

-- Nexus 5548 Layer 3 Daughter Card, Version 2

cevN5kC5596TFAFixedModule  OBJECT IDENTIFIER
    ::= { cevModuleN5KType 22 }

-- The fixed module that has 48 10G BaseT ports + supervisor in Nexus 5596

cevN5KN55M12T  OBJECT IDENTIFIER
    ::= { cevModuleN5KType 23 }

-- Expansion Module, 12x10GE

cevN5KN55M4Q  OBJECT IDENTIFIER
    ::= { cevModuleN5KType 24 }

-- Expansion Module, 4x40GE (requires QSFP)

cevModuleASA5505Type  OBJECT IDENTIFIER
    ::= { cevModule 73 }

-- Group for the ASA5505 Type of cards

cevMASA5505IsmSscIps5K9  OBJECT IDENTIFIER
    ::= { cevModuleASA5505Type 1 }

-- Model 5 IPS Security Services Card for the ASA 5505

cevModuleASR9KType  OBJECT IDENTIFIER
    ::= { cevModule 74 }

-- Cisco Aggregation Services Router 90xx Module

cevModuleA9K8x10GEB  OBJECT IDENTIFIER
    ::= { cevModuleASR9KType 1 }

-- 8-Port 10GE DX Line Card, Requires XFPs

cevModuleA9K8x10GEE  OBJECT IDENTIFIER
    ::= { cevModuleASR9KType 2 }

-- 8-Port 10GE DX Extended Line Card, Requires XFPs

cevModuleA9K4x10GEB  OBJECT IDENTIFIER
    ::= { cevModuleASR9KType 3 }

-- 4-Port 10GE Line Card, Requires XFPs

cevModuleA9K4x10GEE  OBJECT IDENTIFIER
    ::= { cevModuleASR9KType 4 }

-- 4-Port 10GE Extended Line Card, Requires XFPs

cevModuleA9K40x1GEB  OBJECT IDENTIFIER
    ::= { cevModuleASR9KType 5 }

-- 40-Port GE Line Card, Requires SFPs

cevModuleA9K40x1GEE  OBJECT IDENTIFIER
    ::= { cevModuleASR9KType 6 }

-- 40-Port GE Extended Line Card, Requires SFPs

cevModuleA9KRSP  OBJECT IDENTIFIER
    ::= { cevModuleASR9KType 7 }

-- ASR9K Fabric, Controller, 2G memory

cevModuleA9KRSP4G  OBJECT IDENTIFIER
    ::= { cevModuleASR9KType 8 }

-- ASR9K Fabric, Controller, 4G memory

cevModuleASR9KHost  OBJECT IDENTIFIER
    ::= { cevModuleASR9KType 9 }

-- Cisco ASR9K RSP/LC Host module

cevModuleA9KServiceAcceleratorModule  OBJECT IDENTIFIER
    ::= { cevModuleASR9KType 24 }

-- SAM: ServiceAcceleratorModule Flash cards

cevModuleA9KRsp440Se  OBJECT IDENTIFIER
    ::= { cevModuleASR9KType 25 }

-- ASR 9000 RSP-440 Service Edge Optimized

cevModuleA9KRsp440Tr  OBJECT IDENTIFIER
    ::= { cevModuleASR9KType 26 }

-- ASR 9000 RSP-440 Packet Transport Optimized

cevModuleA9K1X100GeSe  OBJECT IDENTIFIER
    ::= { cevModuleASR9KType 27 }

-- ASR 9000 1-port 100GE, Service Edge Optimized LC

cevModuleA9K1X100GeTr  OBJECT IDENTIFIER
    ::= { cevModuleASR9KType 28 }

-- ASR 9000 1-port 100GE, Packet Transport Optimized LC

cevModuleA9K36X10GeSe  OBJECT IDENTIFIER
    ::= { cevModuleASR9KType 29 }

-- ASR 9000 36-port 10GE, Service Edge Optimized LC

cevModuleA9K36X10GeTr  OBJECT IDENTIFIER
    ::= { cevModuleASR9KType 30 }

-- ASR 9000 36-port 10GE, Packet Transport Optimized LC

cevModuleA9K2X100GeSe  OBJECT IDENTIFIER
    ::= { cevModuleASR9KType 31 }

-- ASR 9000 2-port 100GE, Service Edge Optimized LC

cevModuleA9K2X100GeTr  OBJECT IDENTIFIER
    ::= { cevModuleASR9KType 32 }

-- ASR 9000 2-port 100GE, Packet Transport Optimized LC

cevModuleA9K24X10GeSe  OBJECT IDENTIFIER
    ::= { cevModuleASR9KType 33 }

-- ASR 9000 24-port 10GE, Service Edge Optimized LC

cevModuleA9K24X10GeTr  OBJECT IDENTIFIER
    ::= { cevModuleASR9KType 34 }

-- ASR 9000 24-port 10GE, Packet Transport Optimized LC

cevModuleA9KMOD80SE  OBJECT IDENTIFIER
    ::= { cevModuleASR9KType 35 }

-- ASR 9000 MOD80 Modular Linecard, Service Edge Optimized

cevModuleA9KMOD80TR  OBJECT IDENTIFIER
    ::= { cevModuleASR9KType 36 }

-- ASR 9000 MOD80 Modular Linecard, Packet Transport Optimized

cevModuleA9KMOD160SE  OBJECT IDENTIFIER
    ::= { cevModuleASR9KType 37 }

-- ASR 9000 MOD160 Modular Linecard, Service Edge Optimized

cevModuleA9KMOD160TR  OBJECT IDENTIFIER
    ::= { cevModuleASR9KType 38 }

-- ASR 9000 MOD160 Modular Linecard, Packet Transport Optimized

cevModuleA9K9922RpSe  OBJECT IDENTIFIER
    ::= { cevModuleASR9KType 39 }

-- ASR 9922 Route Processor for Service Edge

cevModuleA9K9922RpTr  OBJECT IDENTIFIER
    ::= { cevModuleASR9KType 40 }

-- ASR 9922 Route Processor for Packet Transport

cevModuleA9K9922Sfc110  OBJECT IDENTIFIER
    ::= { cevModuleASR9KType 41 }

-- ASR 9922 Switch Fabric Card/110G

cevModuleA9KVGenericLc  OBJECT IDENTIFIER
    ::= { cevModuleASR9KType 42 }

-- ASR-9000v Generic Line Card

cevModuleA9K9912SFC110  OBJECT IDENTIFIER
    ::= { cevModuleASR9KType 43 }

-- ASR 9912 Switch Fabric Card/110G

cevModuleA9K9912RpTr  OBJECT IDENTIFIER
    ::= { cevModuleASR9KType 44 }

-- ASR 9912 Route Processor for Packet Transport

cevModuleA9K9912RpSe  OBJECT IDENTIFIER
    ::= { cevModuleASR9KType 45 }

-- ASR 9912 Route Processor Service Edge

cevModuleA9KMODULEv  OBJECT IDENTIFIER
    ::= { cevModuleASR9KType 46 }

-- ASR 9000 Virtual Module

cevModuleA9K9001Lc  OBJECT IDENTIFIER
    ::= { cevModuleASR9KType 47 }

-- ASR 9001, Modular Line Card

cevModuleA9K9001Rp  OBJECT IDENTIFIER
    ::= { cevModuleASR9KType 48 }

-- ASR 9001, Route Switch Processor with 8GB memory

cevModuleA9KSip7008G  OBJECT IDENTIFIER
    ::= { cevModuleASR9KType 49 }

-- Cisco ASR9000 Series SPA Interface Processor 700 with 8G memory

cevModuleA9K9001LcS  OBJECT IDENTIFIER
    ::= { cevModuleASR9KType 53 }

-- ASR 9001 Modular Line Card low speed

cevModuleA9KVSM500  OBJECT IDENTIFIER
    ::= { cevModuleASR9KType 54 }

-- ASR9K Virtualized Services Module

cevModuleASR14KType  OBJECT IDENTIFIER
    ::= { cevModule 75 }

-- Represents the base class for all modules used in ASR14000 Series

cevModuleASR14K20x1GeFl  OBJECT IDENTIFIER
    ::= { cevModuleASR14KType 1 }

-- Cisco ASR14000 Series 20x1GE Flexible Interface Module

cevModuleASR14K42x1GE  OBJECT IDENTIFIER
    ::= { cevModuleASR14KType 2 }

-- Cisco ASR14000 Series 42x1GE Interface Module

cevModuleASR14K4x10GE  OBJECT IDENTIFIER
    ::= { cevModuleASR14KType 3 }

-- ASR14000 Series 4x10GE Interface Module

cevModuleASR14K4FabricCard  OBJECT IDENTIFIER
    ::= { cevModuleASR14KType 4 }

-- Cisco ASR14000 Series 4-Slot chassis Fabric Card

cevModuleASR14K8FabricCard  OBJECT IDENTIFIER
    ::= { cevModuleASR14KType 5 }

-- Cisco ASR14000 Series 8-Slot chassis Fabric Card

cevModuleASR14KRP  OBJECT IDENTIFIER
    ::= { cevModuleASR14KType 6 }

-- Cisco ASR14000 Series Route Processor

cevModuleASR14KFP40  OBJECT IDENTIFIER
    ::= { cevModuleASR14KType 7 }

-- Cisco ASR14000 Series Forwarding Processor 40G

cevModuleASR14KFPE  OBJECT IDENTIFIER
    ::= { cevModuleASR14KType 8 }

-- Cisco ASR14000 Series Enhanced Forwarding Processor 40G

cevModuleASR14K2x10WLFL  OBJECT IDENTIFIER
    ::= { cevModuleASR14KType 9 }

-- Cisco ASR14000 Series 2X10GE WAN/LAN Flexible Interface Module

cevModuleSFPPlusS  OBJECT IDENTIFIER
    ::= { cevModule 76 }

-- Group for SFP+S Type of Cards

cevSFP10GLR  OBJECT IDENTIFIER
    ::= { cevModuleSFPPlusS 1 }

-- 10GBASE-LR SFP+ Module for SMF

cevSFP10GLRM  OBJECT IDENTIFIER
    ::= { cevModuleSFPPlusS 2 }

-- 10GBASE-LRM SFP+ Module for MMF

cevSFP10GSR  OBJECT IDENTIFIER
    ::= { cevModuleSFPPlusS 3 }

-- 10GBASE-SR SFP+ Module for MMF

cevSFP10GUSR  OBJECT IDENTIFIER
    ::= { cevModuleSFPPlusS 4 }

-- 10GBASE-USR SFP+ Module for MMF

cevSFP10GER  OBJECT IDENTIFIER
    ::= { cevModuleSFPPlusS 5 }

-- 10GBASE-ER SFP+ Module for SMF

cevSFP10GLRMSM  OBJECT IDENTIFIER
    ::= { cevModuleSFPPlusS 7 }

-- 10GBASE-LRM-SM SFP+ Module for SMF

cevSFP10GZR  OBJECT IDENTIFIER
    ::= { cevModuleSFPPlusS 8 }

-- 10GBASE-ZR SFP+ Module for SMF

cevSFP10GCU1M  OBJECT IDENTIFIER
    ::= { cevModuleSFPPlusS 9 }

-- 10GBASE-CU SFP+ Cable 1 Meter, passive

cevSFP10GCU3M  OBJECT IDENTIFIER
    ::= { cevModuleSFPPlusS 10 }

-- 10GBASE-CU SFP+ Cable 3 Meter, passive

cevSFP10GCU5M  OBJECT IDENTIFIER
    ::= { cevModuleSFPPlusS 11 }

-- 10GBASE-CU SFP+ Cable 5 Meter, passive

cevSFP10GACU7M  OBJECT IDENTIFIER
    ::= { cevModuleSFPPlusS 12 }

-- 10GBASE-CU SFP+ Cable 7 Meter, active

cevSFPH10GbAcu10m  OBJECT IDENTIFIER
    ::= { cevModuleSFPPlusS 13 }

-- 10GBASE-CU SFP+ Cable 7 Meter, active

cevSFPOe8541  OBJECT IDENTIFIER
    ::= { cevModuleSFPPlusS 14 }

-- SFP for Oe8541

cevSFPOe7571  OBJECT IDENTIFIER
    ::= { cevModuleSFPPlusS 15 }

-- SFP for Oe7571

cevSFPOe7541  OBJECT IDENTIFIER
    ::= { cevModuleSFPPlusS 16 }

-- SFP for Oe7541

cevSFPOe694  OBJECT IDENTIFIER
    ::= { cevModuleSFPPlusS 17 }

-- SFP for Oe694

cevSFPOe594  OBJECT IDENTIFIER
    ::= { cevModuleSFPPlusS 18 }

-- SFP for Oe594

cevSFPOe294  OBJECT IDENTIFIER
    ::= { cevModuleSFPPlusS 19 }

-- SFP for Oe294

cevSFPDwdmSfp10g3190  OBJECT IDENTIFIER
    ::= { cevModuleSFPPlusS 20 }

-- 10GBASE-DWDM 1531.90 nm SFP+ (100-GHz ITU grid)

cevSFPDwdmSfp10g3112  OBJECT IDENTIFIER
    ::= { cevModuleSFPPlusS 21 }

-- 10GBASE-DWDM 1531.12 nm SFP+ (100-GHz ITU grid)

cevSFPDwdmSfp10g3033  OBJECT IDENTIFIER
    ::= { cevModuleSFPPlusS 22 }

-- 10GBASE-DWDM 1530.33 nm SFP+ (100-GHz ITU grid)

cevSFPDwdmSfp10g3582  OBJECT IDENTIFIER
    ::= { cevModuleSFPPlusS 23 }

-- 10GBASE-DWDM 1535.82 nm SFP+ (100-GHz ITU grid)

cevSFPDwdmSfp10g3504  OBJECT IDENTIFIER
    ::= { cevModuleSFPPlusS 24 }

-- 10GBASE-DWDM 1535.04 nm SFP+ (100-GHz ITU grid)

cevSFPDwdmSfp10g3425  OBJECT IDENTIFIER
    ::= { cevModuleSFPPlusS 25 }

-- 10GBASE-DWDM 1534.25 nm SFP+ (100-GHz ITU grid)

cevSFPDwdmSfp10g3347  OBJECT IDENTIFIER
    ::= { cevModuleSFPPlusS 26 }

-- 10GBASE-DWDM 1533.47 nm SFP+ (100-GHz ITU grid)

cevSFPDwdmSfp10g3268  OBJECT IDENTIFIER
    ::= { cevModuleSFPPlusS 27 }

-- 10GBASE-DWDM 1532.68 nm SFP+ (100-GHz ITU grid)

cevSFPDwdmSfp10g3977  OBJECT IDENTIFIER
    ::= { cevModuleSFPPlusS 28 }

-- 10GBASE-DWDM 1539.77 nm SFP+ (100-GHz ITU grid)

cevSFPDwdmSfp10g3898  OBJECT IDENTIFIER
    ::= { cevModuleSFPPlusS 29 }

-- 10GBASE-DWDM 1538.98 nm SFP+ (100-GHz ITU grid)

cevSFPDwdmSfp10g3819  OBJECT IDENTIFIER
    ::= { cevModuleSFPPlusS 30 }

-- 10GBASE-DWDM 1538.19 nm SFP+ (100-GHz ITU grid)

cevSFPDwdmSfp10g3740  OBJECT IDENTIFIER
    ::= { cevModuleSFPPlusS 31 }

-- 10GBASE-DWDM 1537.40 nm SFP+ (100-GHz ITU grid)

cevSFPDwdmSfp10g3661  OBJECT IDENTIFIER
    ::= { cevModuleSFPPlusS 32 }

-- 10GBASE-DWDM 1536.61 nm SFP+ (100-GHz ITU grid)

cevSFPDwdmSfp10g4373  OBJECT IDENTIFIER
    ::= { cevModuleSFPPlusS 33 }

-- 10GBASE-DWDM 1543.73 nm SFP+ (100-GHz ITU grid)

cevSFPDwdmSfp10g4294  OBJECT IDENTIFIER
    ::= { cevModuleSFPPlusS 34 }

-- 10GBASE-DWDM 1542.94 nm SFP+ (100-GHz ITU grid)

cevSFPDwdmSfp10g4214  OBJECT IDENTIFIER
    ::= { cevModuleSFPPlusS 35 }

-- 10GBASE-DWDM 1542.14 nm SFP+ (100-GHz ITU grid)

cevSFPDwdmSfp10g4135  OBJECT IDENTIFIER
    ::= { cevModuleSFPPlusS 36 }

-- 10GBASE-DWDM 1541.35 nm SFP+ (100-GHz ITU grid)

cevSFPDwdmSfp10g4056  OBJECT IDENTIFIER
    ::= { cevModuleSFPPlusS 37 }

-- 10GBASE-DWDM 1540.56 nm SFP+ (100-GHz ITU grid)

cevSFPDwdmSfp10g4772  OBJECT IDENTIFIER
    ::= { cevModuleSFPPlusS 38 }

-- 10GBASE-DWDM 1547.72 nm SFP+ (100-GHz ITU grid)

cevSFPDwdmSfp10g4692  OBJECT IDENTIFIER
    ::= { cevModuleSFPPlusS 39 }

-- 10GBASE-DWDM 1546.92 nm SFP+ (100-GHz ITU grid)

cevSFPDwdmSfp10g4612  OBJECT IDENTIFIER
    ::= { cevModuleSFPPlusS 40 }

-- 10GBASE-DWDM 1546.12 nm SFP+ (100-GHz ITU grid)

cevSFPDwdmSfp10g4532  OBJECT IDENTIFIER
    ::= { cevModuleSFPPlusS 41 }

-- 10GBASE-DWDM 1545.32 nm SFP+ (100-GHz ITU grid)

cevSFPDwdmSfp10g5172  OBJECT IDENTIFIER
    ::= { cevModuleSFPPlusS 42 }

-- 10GBASE-DWDM 1551.72 nm SFP+ (100-GHz ITU grid)

cevSFPDwdmSfp10g5092  OBJECT IDENTIFIER
    ::= { cevModuleSFPPlusS 43 }

-- 10GBASE-DWDM 1550.92 nm SFP+ (100-GHz ITU grid)

cevSFPDwdmSfp10g5012  OBJECT IDENTIFIER
    ::= { cevModuleSFPPlusS 44 }

-- 10GBASE-DWDM 1550.12 nm SFP+ (100-GHz ITU grid)

cevSFPDwdmSfp10g4932  OBJECT IDENTIFIER
    ::= { cevModuleSFPPlusS 45 }

-- 10GBASE-DWDM 1549.32 nm SFP+ (100-GHz ITU grid)

cevSFPDwdmSfp10g4851  OBJECT IDENTIFIER
    ::= { cevModuleSFPPlusS 46 }

-- 10GBASE-DWDM 1548.51 nm SFP+ (100-GHz ITU grid)

cevSFPDwdmSfp10g5575  OBJECT IDENTIFIER
    ::= { cevModuleSFPPlusS 47 }

-- 10GBASE-DWDM 1555.75 nm SFP+ (100-GHz ITU grid)

cevSFPDwdmSfp10g5494  OBJECT IDENTIFIER
    ::= { cevModuleSFPPlusS 48 }

-- 10GBASE-DWDM 1554.94 nm SFP+ (100-GHz ITU grid)

cevSFPDwdmSfp10g5413  OBJECT IDENTIFIER
    ::= { cevModuleSFPPlusS 49 }

-- 10GBASE-DWDM 1554.13 nm SFP+ (100-GHz ITU grid)

cevSFPDwdmSfp10g5333  OBJECT IDENTIFIER
    ::= { cevModuleSFPPlusS 50 }

-- 10GBASE-DWDM 1553.33 nm SFP+ (100-GHz ITU grid)

cevSFPDwdmSfp10g5252  OBJECT IDENTIFIER
    ::= { cevModuleSFPPlusS 51 }

-- 10GBASE-DWDM 1552.52 nm SFP+ (100-GHz ITU grid)

cevSFPDwdmSfp10g5979  OBJECT IDENTIFIER
    ::= { cevModuleSFPPlusS 52 }

-- 10GBASE-DWDM 1559.79 nm SFP+ (100-GHz ITU grid)

cevSFPDwdmSfp10g5898  OBJECT IDENTIFIER
    ::= { cevModuleSFPPlusS 53 }

-- 10GBASE-DWDM 1558.98 nm SFP+ (100-GHz ITU grid)

cevSFPDwdmSfp10g5817  OBJECT IDENTIFIER
    ::= { cevModuleSFPPlusS 54 }

-- 10GBASE-DWDM 1558.17 nm SFP+ (100-GHz ITU grid)

cevSFPDwdmSfp10g5736  OBJECT IDENTIFIER
    ::= { cevModuleSFPPlusS 55 }

-- 10GBASE-DWDM 1557.36 nm SFP+ (100-GHz ITU grid)

cevSFPDwdmSfp10g5655  OBJECT IDENTIFIER
    ::= { cevModuleSFPPlusS 56 }

-- 10GBASE-DWDM 1556.55 nm SFP+ (100-GHz ITU grid)

cevSFPDwdmSfp10g6061  OBJECT IDENTIFIER
    ::= { cevModuleSFPPlusS 57 }

-- 10GBASE-DWDM 1560.61 nm SFP+ (100-GHz ITU grid)

cevSFPDwdmSfp10g6141  OBJECT IDENTIFIER
    ::= { cevModuleSFPPlusS 58 }

-- 10GBASE-DWDM 1561.41 nm SFP+ (100-GHz ITU grid)

cevSFPDwdmSfp10g4453  OBJECT IDENTIFIER
    ::= { cevModuleSFPPlusS 59 }

-- 10GBASE-DWDM 1544.53 nm SFP+ (100-GHz ITU grid)

cevSFPFET10G  OBJECT IDENTIFIER
    ::= { cevModuleSFPPlusS 60 }

-- 10G Line Extender for FEX

cevSFPSC10GTDwdmC  OBJECT IDENTIFIER
    ::= { cevModuleSFPPlusS 61 }

-- 10G MR, Full C Band Tuneable DWDM SFP+, 50 Ghz, LC

cevSFPSC10GSR  OBJECT IDENTIFIER
    ::= { cevModuleSFPPlusS 62 }

-- 10GBASE-SR SFP+ Module for MMF-Commercial Temp

cevSFPSC10GER  OBJECT IDENTIFIER
    ::= { cevModuleSFPPlusS 63 }

-- 10GBASE-ER SFP+ Module for SMF-Commercial Temp

cevSFPSC10GLR  OBJECT IDENTIFIER
    ::= { cevModuleSFPPlusS 64 }

-- 10GBASE-LR SFP+ Module for SMF-Commercial Temp

cevSFPSC10GZR  OBJECT IDENTIFIER
    ::= { cevModuleSFPPlusS 65 }

-- 10GBASE-ZR SFP+ Module for SMF-Commercial Temp

cevSFPSE10GLR  OBJECT IDENTIFIER
    ::= { cevModuleSFPPlusS 66 }

-- 10GBASE-LR SE SFP+ Module for MMF-Commercial Temp

cevSFPSC10G303  OBJECT IDENTIFIER
    ::= { cevModuleSFPPlusS 67 }

-- 10G MR, SFP+ 1530.33, 100 GHz, LC

cevSFPSC10G311  OBJECT IDENTIFIER
    ::= { cevModuleSFPPlusS 68 }

-- 10G MR, SFP+ 1531.12, 100 GHz, LC

cevSFPSC10G319  OBJECT IDENTIFIER
    ::= { cevModuleSFPPlusS 69 }

-- 10G MR, SFP+ 1531.90, 100 GHz, LC

cevSFPSC10G326  OBJECT IDENTIFIER
    ::= { cevModuleSFPPlusS 70 }

-- 10G MR, SFP+ 1532.68, 100 GHz, LC

cevSFPSC10G334  OBJECT IDENTIFIER
    ::= { cevModuleSFPPlusS 71 }

-- 10G MR, SFP+ 1533.47, 100 GHz, LC

cevSFPSC10G342  OBJECT IDENTIFIER
    ::= { cevModuleSFPPlusS 72 }

-- 10G MR, SFP+ 1534.25, 100 GHz, LC

cevSFPSC10G350  OBJECT IDENTIFIER
    ::= { cevModuleSFPPlusS 73 }

-- 10G MR, SFP+ 1535.04, 100 GHz, LC

cevSFPSC10G358  OBJECT IDENTIFIER
    ::= { cevModuleSFPPlusS 74 }

-- 10G MR, SFP+ 1535.82, 100 GHz, LC

cevSFPSC10G366  OBJECT IDENTIFIER
    ::= { cevModuleSFPPlusS 75 }

-- 10G MR, SFP+ 1536.61, 100 GHz, LC

cevSFPSC10G374  OBJECT IDENTIFIER
    ::= { cevModuleSFPPlusS 76 }

-- 10G MR, SFP+ 1537.40, 100 GHz, LC

cevSFPSC10G381  OBJECT IDENTIFIER
    ::= { cevModuleSFPPlusS 77 }

-- 10G MR, SFP+ 1538.19, 100 GHz, LC

cevSFPSC10G389  OBJECT IDENTIFIER
    ::= { cevModuleSFPPlusS 78 }

-- 10G MR, SFP+ 1538.98, 100 GHz, LC

cevSFPSC10G397  OBJECT IDENTIFIER
    ::= { cevModuleSFPPlusS 79 }

-- 10G MR, SFP+ 1539.77, 100 GHz, LC

cevSFPSC10G405  OBJECT IDENTIFIER
    ::= { cevModuleSFPPlusS 80 }

-- 10G MR, SFP+ 1540.56, 100 GHz, LC

cevSFPSC10G415  OBJECT IDENTIFIER
    ::= { cevModuleSFPPlusS 81 }

-- 10G MR, SFP+ 1541.35, 100 GHz, LC

cevSFPSC10G421  OBJECT IDENTIFIER
    ::= { cevModuleSFPPlusS 82 }

-- 10G MR, SFP+ 1542.14, 100 GHz, LC

cevSFPSC10G429  OBJECT IDENTIFIER
    ::= { cevModuleSFPPlusS 83 }

-- 10G MR, SFP+ 1542.94, 100 GHz, LC

cevSFPSC10G437  OBJECT IDENTIFIER
    ::= { cevModuleSFPPlusS 84 }

-- 10G MR, SFP+ 1543.73, 100 GHz, LC

cevSFPSC10G445  OBJECT IDENTIFIER
    ::= { cevModuleSFPPlusS 85 }

-- 10G MR, SFP+ 1544.53, 100 GHz, LC

cevSFPSC10G453  OBJECT IDENTIFIER
    ::= { cevModuleSFPPlusS 86 }

-- 10G MR, SFP+ 1545.32, 100 GHz, LC

cevSFPSC10G461  OBJECT IDENTIFIER
    ::= { cevModuleSFPPlusS 87 }

-- 10G MR, SFP+ 1546.12, 100 GHz, LC

cevSFPSC10G469  OBJECT IDENTIFIER
    ::= { cevModuleSFPPlusS 88 }

-- 10G MR, SFP+ 1546.92, 100 GHz, LC

cevSFPSC10G477  OBJECT IDENTIFIER
    ::= { cevModuleSFPPlusS 89 }

-- 10G MR, SFP+ 1547.72, 100 GHz, LC

cevSFPSC10G485  OBJECT IDENTIFIER
    ::= { cevModuleSFPPlusS 90 }

-- 10G MR, SFP+ 1548.51, 100 GHz, LC

cevSFPSC10G493  OBJECT IDENTIFIER
    ::= { cevModuleSFPPlusS 91 }

-- 10G MR, SFP+ 1549.32, 100 GHz, LC

cevSFPSC10G501  OBJECT IDENTIFIER
    ::= { cevModuleSFPPlusS 92 }

-- 10G MR, SFP+ 1550.12, 100 GHz, LC

cevSFPSC10G509  OBJECT IDENTIFIER
    ::= { cevModuleSFPPlusS 93 }

-- 10G MR, SFP+ 1550.92, 100 GHz, LC

cevSFPSC10G517  OBJECT IDENTIFIER
    ::= { cevModuleSFPPlusS 94 }

-- 10G MR, SFP+ 1551.72, 100 GHz, LC

cevSFPSC10G525  OBJECT IDENTIFIER
    ::= { cevModuleSFPPlusS 95 }

-- 10G MR, SFP+ 1552.52, 100 GHz, LC

cevSFPSC10G533  OBJECT IDENTIFIER
    ::= { cevModuleSFPPlusS 96 }

-- 10G MR, SFP+ 1553.33, 100 GHz, LC

cevSFPSC10G541  OBJECT IDENTIFIER
    ::= { cevModuleSFPPlusS 97 }

-- 10G MR, SFP+ 1554.13, 100 GHz, LC

cevSFPSC10G549  OBJECT IDENTIFIER
    ::= { cevModuleSFPPlusS 98 }

-- 10G MR, SFP+ 1554.94, 100 GHz, LC

cevSFPSC10G557  OBJECT IDENTIFIER
    ::= { cevModuleSFPPlusS 99 }

-- 10G MR, SFP+ 1555.75, 100 GHz, LC

cevSFPSC10G565  OBJECT IDENTIFIER
    ::= { cevModuleSFPPlusS 100 }

-- 10G MR, SFP+ 1556.55, 100 GHz, LC

cevSFPSC10G573  OBJECT IDENTIFIER
    ::= { cevModuleSFPPlusS 101 }

-- 10G MR, SFP+ 1557.36, 100 GHz, LC

cevSFPSC10G581  OBJECT IDENTIFIER
    ::= { cevModuleSFPPlusS 102 }

-- 10G MR, SFP+ 1558.17, 100 GHz, LC

cevSFPSC10G589  OBJECT IDENTIFIER
    ::= { cevModuleSFPPlusS 103 }

-- 10G MR, SFP+ 1558.98, 100 GHz, LC

cevSFPSC10G597  OBJECT IDENTIFIER
    ::= { cevModuleSFPPlusS 104 }

-- 10G MR, SFP+ 1559.79, 100 GHz, LC

cevSFPSC10G606  OBJECT IDENTIFIER
    ::= { cevModuleSFPPlusS 105 }

-- 10G MR, SFP+ 1560.61, 100 GHz, LC

cevSFPSC10G614  OBJECT IDENTIFIER
    ::= { cevModuleSFPPlusS 106 }

-- 10G MR, SFP+ 1561.43, 100 GHz, LC

cevDirectAttachCable10Gs  OBJECT IDENTIFIER
    ::= { cevModule 77 }

-- Group for DirectAttachCable10Gs Type of Cards

cevSFPH10GBCU1M  OBJECT IDENTIFIER
    ::= { cevDirectAttachCable10Gs 1 }

-- 10GBASE-CU SFP+ Cable 1 Meter

cevSFPH10GBCU5M  OBJECT IDENTIFIER
    ::= { cevDirectAttachCable10Gs 2 }

-- 10GBASE-CU SFP+ Cable 5 Meter

cevSFPH10GBCU3M  OBJECT IDENTIFIER
    ::= { cevDirectAttachCable10Gs 3 }

-- 10GBASE-CU SFP+ Cable 3 Meter

cevSFPH10GBCU7M  OBJECT IDENTIFIER
    ::= { cevDirectAttachCable10Gs 4 }

-- 10GBASE-CU SFP+ Cable 7 Meter

cevSFPH10GBACU1M  OBJECT IDENTIFIER
    ::= { cevDirectAttachCable10Gs 9 }

-- 10GBASE-Active CU SFP+ Cable 1 Meter

cevSFPH10GBACU3M  OBJECT IDENTIFIER
    ::= { cevDirectAttachCable10Gs 10 }

-- 10GBASE-Active CU SFP+ Cable 3 Meter

cevSFPH10GBACU5M  OBJECT IDENTIFIER
    ::= { cevDirectAttachCable10Gs 11 }

-- 10GBASE-Active CU SFP+ Cable 5 Meter

cevSFPH10GBACU15M  OBJECT IDENTIFIER
    ::= { cevDirectAttachCable10Gs 12 }

-- 10GBASE-Active CU SFP+ Cable 15 Meter

cevSFPH10GBACU10M  OBJECT IDENTIFIER
    ::= { cevDirectAttachCable10Gs 13 }

-- 10GBASE-Active CU SFP+ Cable 10 Meter

cevSFPH10GBACU7M  OBJECT IDENTIFIER
    ::= { cevDirectAttachCable10Gs 14 }

-- 10GBASE-Active CU SFP+ Cable 7 Meter

cevSFPH10GBCU150CM  OBJECT IDENTIFIER
    ::= { cevDirectAttachCable10Gs 15 }

-- 10GBASE-CU SFP+ Cable 1.5 Meter

cevSFPH10GBCU250CM  OBJECT IDENTIFIER
    ::= { cevDirectAttachCable10Gs 16 }

-- 10GBASE-CU SFP+ Cable 2.5 Meter

cevSFP10GAOC1M  OBJECT IDENTIFIER
    ::= { cevDirectAttachCable10Gs 17 }

-- 10GBASE Active Optical SFP+ Cable, 1M

cevSFP10GAOC2M  OBJECT IDENTIFIER
    ::= { cevDirectAttachCable10Gs 18 }

-- 10GBASE Active Optical SFP+ Cable, 2M

cevSFP10GAOC3M  OBJECT IDENTIFIER
    ::= { cevDirectAttachCable10Gs 19 }

-- 10GBASE Active Optical SFP+ Cable, 3M

cevSFP10GAOC5M  OBJECT IDENTIFIER
    ::= { cevDirectAttachCable10Gs 20 }

-- 10GBASE Active Optical SFP+ Cable, 5M

cevSFP10GAOC7M  OBJECT IDENTIFIER
    ::= { cevDirectAttachCable10Gs 21 }

-- 10GBASE Active Optical SFP+ Cable, 7M

cevSFP10GAOC10M  OBJECT IDENTIFIER
    ::= { cevDirectAttachCable10Gs 22 }

-- 10GBASE Active Optical SFP+ Cable, 10M

cevSFPH10GBCU200CM  OBJECT IDENTIFIER
    ::= { cevDirectAttachCable10Gs 23 }

-- 10GBASE-CU SFP+ Cable 2 Meter

cevModuleN2KType  OBJECT IDENTIFIER
    ::= { cevModule 78 }

-- Group for the Nexus N2K Type of cards

cevN2kC2148T1GEFixedModule  OBJECT IDENTIFIER
    ::= { cevModuleN2KType 1 }

-- The fixed module in N2K-C2148T-1GE

cevN2kC2232PP10GEFixedModule  OBJECT IDENTIFIER
    ::= { cevModuleN2KType 2 }

-- The fixed module in N2K-C2232PP-10GE

cevN2kC2248TP1GEFixedModule  OBJECT IDENTIFIER
    ::= { cevModuleN2KType 3 }

-- The fixed module in N2K-C2248TP-1GE

cevN2kC2224TP1GEFixedModule  OBJECT IDENTIFIER
    ::= { cevModuleN2KType 4 }

-- The fixed module in N2K-C2224TP-1GE

cevN2kC2232TT10GEFixedModule  OBJECT IDENTIFIER
    ::= { cevModuleN2KType 5 }

-- The fixed module in N2K-C2232TT-10GE

cevN2kC2232TP10GEFixedModule  OBJECT IDENTIFIER
    ::= { cevModuleN2KType 6 }

-- The fixed module in N2K-C2232TP-10GE

cevN2kC2248TT1GEFixedModule  OBJECT IDENTIFIER
    ::= { cevModuleN2KType 7 }

-- The fixed module in N2K-C2248TT-1GE

cevN2kB22HPPFixedModule  OBJECT IDENTIFIER
    ::= { cevModuleN2KType 9 }

-- The fixed module in N2K-B22HP-P

cevN2kM2800P  OBJECT IDENTIFIER
    ::= { cevModuleN2KType 10 }

-- N2K-C2232TM-10GE Modular uplink, 8 ports SFP+

cevN2kC2232TM10GEFixedModule  OBJECT IDENTIFIER
    ::= { cevModuleN2KType 11 }

-- The fixed module in N2K-C2232TM-10GE

cevN2kC2232TME10GEFixedModule  OBJECT IDENTIFIER
    ::= { cevModuleN2KType 12 }

-- The fixed module in N2K-C2232TM-E-10GE

cevN2kC2248PQ10GEFixedModule  OBJECT IDENTIFIER
    ::= { cevModuleN2KType 13 }

-- The fixed module in N2K-C2248PQ-10GE

cevN2kB22DELLPFixedModule  OBJECT IDENTIFIER
    ::= { cevModuleN2KType 14 }

-- The fixed module in N2K-B22DELL-P

cevN2kB22FTSPFixedModule  OBJECT IDENTIFIER
    ::= { cevModuleN2KType 15 }

-- The fixed module in N2K-B22FTS-P

cevN2kB22IBMPFixedModule  OBJECT IDENTIFIER
    ::= { cevModuleN2KType 16 }

-- The fixed module in N2K-B22IBM-P

cevModuleN1KVType  OBJECT IDENTIFIER
    ::= { cevModule 79 }

-- Group for the Nexus1000V type of modules

cevN1KVVSM  OBJECT IDENTIFIER
    ::= { cevModuleN1KVType 1 }

-- Virtual Supervisor Module for Nexus1000V

cevN1KVVEM  OBJECT IDENTIFIER
    ::= { cevModuleN1KVType 2 }

-- Virtual Ethernet Module for Nexus1000V

cevN1KVVXLANGateway  OBJECT IDENTIFIER
    ::= { cevModuleN1KVType 3 }

-- VXLAN (Virtual eXtensible LAN) Gateway Service Module

cevN1KVInterCloudExtender  OBJECT IDENTIFIER
    ::= { cevModuleN1KVType 4 }

-- Intercloud Extender Service Module

cevN1KVInterCloudSwitch  OBJECT IDENTIFIER
    ::= { cevModuleN1KVType 5 }

-- Intercloud Switch Service Module

cevModuleUCSType  OBJECT IDENTIFIER
    ::= { cevModule 80 }

-- UCS type Module

cevUCSN10S6100FixedModule  OBJECT IDENTIFIER
    ::= { cevModuleUCSType 1 }

-- Fixed Module within Cisco UCS  Fabric InterConnect

cevUCSN10E0080  OBJECT IDENTIFIER
    ::= { cevModuleUCSType 2 }

-- 8-port 4Gb Fibre Channel Expansion Module for Fabric chassis ( requires SFP+)

cevUCSN10E0440  OBJECT IDENTIFIER
    ::= { cevModuleUCSType 3 }

-- Expansion Module for Fabric Chassis with 4-port 10 Gigabit Ethernet and 4-port FC (requires SFP+) (includes port 10GigE license)

cevUCSN10E0600  OBJECT IDENTIFIER
    ::= { cevModuleUCSType 4 }

-- 6-port 10 Gigabit Ethernet Expansion Module for Fabric Chassis (requires SFP+) (includes 10GigE port license)

cevUCSFIE16UP  OBJECT IDENTIFIER
    ::= { cevModuleUCSType 7 }

-- 16-port 10GE Unified Port Module for UCS 6200 Series

cevUCSFI6248UPFixedModule  OBJECT IDENTIFIER
    ::= { cevModuleUCSType 8 }

-- Fixed Module within Cisco UCS 6248 Fabric InterConnect

cevUCSFI6296UPFixedModule  OBJECT IDENTIFIER
    ::= { cevModuleUCSType 9 }

-- Fixed Module within Cisco UCS 6296 Fabric InterConnect

cevUCSFIDL2  OBJECT IDENTIFIER
    ::= { cevModuleUCSType 10 }

-- UCS 6248 Layer 2 Daughter Card

cevModuleNexus1010Type  OBJECT IDENTIFIER
    ::= { cevModule 81 }

-- This is the module type to represent a Virtual Supervisor Card for the Nexus1010 product

cevNexus1010VSM  OBJECT IDENTIFIER
    ::= { cevModuleNexus1010Type 1 }

-- Virtual Supervisor Module for Nexus1010

cevNexusN1KVSANam  OBJECT IDENTIFIER
    ::= { cevModuleNexus1010Type 2 }

-- Virtual Switch NAM for Nexus1010

cevModuleMxeType  OBJECT IDENTIFIER
    ::= { cevModule 82 }

-- This is the module for Mxe type of cards

cevMxeNpm  OBJECT IDENTIFIER
    ::= { cevModuleMxeType 1 }

-- Network Processing Module for MXE 56xx series platform

cevMxeMpm  OBJECT IDENTIFIER
    ::= { cevModuleMxeType 2 }

-- Media Processing Module for MXE 56xx series platform

cevMxe5600ShelfManager  OBJECT IDENTIFIER
    ::= { cevModuleMxeType 3 }

-- Shelf Manager Module for Cisco MXE 5600 platform

cevModuleASA5585Type  OBJECT IDENTIFIER
    ::= { cevModule 83 }

-- cevModuleASA5585Type chassis

cevASA5585Ssp10  OBJECT IDENTIFIER
    ::= { cevModuleASA5585Type 1 }

-- Cisco Adaptive Security Appliance 5585-X  Security Services Processor-10. This card includes firewall, VPN, remote access functionality

cevASA5585Ssp20  OBJECT IDENTIFIER
    ::= { cevModuleASA5585Type 2 }

-- Cisco Adaptive Security Appliance 5585-X  Security Services Processor-20. This card includes firewall, VPN, remote access functionality

cevASA5585Ssp40  OBJECT IDENTIFIER
    ::= { cevModuleASA5585Type 3 }

-- Cisco Adaptive Security Appliance 5585-X  Security Services Processor-40. This card includes firewall, VPN, remote access functionality

cevASA5585Ssp60  OBJECT IDENTIFIER
    ::= { cevModuleASA5585Type 4 }

-- Cisco Adaptive Security Appliance 5585-X  Security Services Processor-60. This card includes firewall, VPN, remote access functionality

cevASA5585IsmSspIps10  OBJECT IDENTIFIER
    ::= { cevModuleASA5585Type 5 }

-- Cisco Adpative Security Appliance 5585-X IPS Security Services Processor-10

cevASA5585IsmSspIps20  OBJECT IDENTIFIER
    ::= { cevModuleASA5585Type 6 }

-- Cisco Adpative Security Appliance 5585-X IPS Security Services Processor-20

cevASA5585IsmSspIps40  OBJECT IDENTIFIER
    ::= { cevModuleASA5585Type 7 }

-- Cisco Adpative Security Appliance 5585-X IPS Security Services Processor-40

cevASA5585IsmSspIps60  OBJECT IDENTIFIER
    ::= { cevModuleASA5585Type 8 }

-- Cisco Adpative Security Appliance 5585-X IPS Security Services Processor-60

cevMASA5585Ssp10K7  OBJECT IDENTIFIER
    ::= { cevModuleASA5585Type 9 }

-- Cisco Adaptive Security Appliance 5585-X Security Services Processor-10. This card provides firewall with No Payload Encryption

cevMASA5585Ssp20K7  OBJECT IDENTIFIER
    ::= { cevModuleASA5585Type 10 }

-- Cisco Adaptive Security Appliance 5585-X Security Services Processor-20. This card provides firewall with No Payload Encryption

cevMASA5585Ssp40K7  OBJECT IDENTIFIER
    ::= { cevModuleASA5585Type 11 }

-- Cisco Adaptive Security Appliance 5585-X Security Services Processor-40. This card provides firewall with No Payload Encryption

cevMASA5585Ssp60K7  OBJECT IDENTIFIER
    ::= { cevModuleASA5585Type 12 }

-- Cisco Adaptive Security Appliance 5585-X Security Services Processor-60. This card provides firewall with No Payload Encryption

cevMASA5585IsmSspIps10K7  OBJECT IDENTIFIER
    ::= { cevModuleASA5585Type 13 }

-- Cisco Adaptive Security Appliance 5585-X IPS Security Services Processor-10

cevMASA5585IsmSspIps20K7  OBJECT IDENTIFIER
    ::= { cevModuleASA5585Type 14 }

-- Cisco Adaptive Security Appliance 5585-X IPS Security Services Processor-20

cevMASA5585IsmSspIps40K7  OBJECT IDENTIFIER
    ::= { cevModuleASA5585Type 15 }

-- Cisco Adaptive Security Appliance 5585-X IPS Security Services Processor-40

cevMASA5585IsmSspIps60K7  OBJECT IDENTIFIER
    ::= { cevModuleASA5585Type 16 }

-- Cisco Adaptive Security Appliance 5585-X IPS Security Services Processor-60

cevMASA5585Nm8x10GE  OBJECT IDENTIFIER
    ::= { cevModuleASA5585Type 17 }

-- Cisco Adaptive Security Appliance 5585-XHalf Width 8 TenGigabit Ethernet Network Module This card includes 8 TenGigabit Ethernet I/O ports

cevMASA5585Nm4x10GE  OBJECT IDENTIFIER
    ::= { cevModuleASA5585Type 18 }

-- Cisco Adaptive Security Appliance 5585-XHalf Width 4 TenGigabit Ethernet Network Module This card includes 4 TenGigabit Ethernet I/O ports

cevMASA5585Nm20x1GE  OBJECT IDENTIFIER
    ::= { cevModuleASA5585Type 19 }

-- Cisco Adaptive Security Appliance 5585-X Half Width 20 Gigabit Ethernet Network Module. This card includes 20 Gigabit Ethernet I/O ports

cevModuleCFPs  OBJECT IDENTIFIER
    ::= { cevModule 84 }

-- group for CFP Module

cevCFP100GLR4  OBJECT IDENTIFIER
    ::= { cevModuleCFPs 1 }

-- 100GBASE-LR4 CFP Module for SMF

cevCFP40GLR4  OBJECT IDENTIFIER
    ::= { cevModuleCFPs 2 }

-- 40GBASE-LR4 CFP Module for SMF

cevCFP40GSR4  OBJECT IDENTIFIER
    ::= { cevModuleCFPs 3 }

-- 40GBASE-SR4 CFP Module for MMF - 4 channels

cevCFP40GFR  OBJECT IDENTIFIER
    ::= { cevModuleCFPs 4 }

-- 40GBASE-FR CFP Module for SMF

cevCFP100GSR10  OBJECT IDENTIFIER
    ::= { cevModuleCFPs 5 }

-- 100GBASE-SR10 CFP, 100m OM3 MMF

cevModuleN3KType  OBJECT IDENTIFIER
    ::= { cevModule 85 }

-- Group for the Nexus 3000 Type of cards

cevN3kC3064PQfixedModule  OBJECT IDENTIFIER
    ::= { cevModuleN3KType 1 }

-- Nexus 3000 Series 1 RU fixed module with 48 SFP+ and and 4 QSFP ports

cevN3kC3064PQ10GEFixedModule  OBJECT IDENTIFIER
    ::= { cevModuleN3KType 2 }

-- Nexus 3000 Series 1 RU fixed module with  48 SFP+ and 4 QSFP ports

cevN3kC3048TP1GEFixedModule  OBJECT IDENTIFIER
    ::= { cevModuleN3KType 3 }

-- Nexus 3000 Series 1 RU fixed module with 48x1G-BaseT and 4x10GE SFP+ ports

cevN3kC3016Q40GEFixedModule  OBJECT IDENTIFIER
    ::= { cevModuleN3KType 4 }

-- Nexus 3000 Series 1 RU fixed module with 16x40GE QSFP ports

cevN3kC3064Pq10GXFixedModule  OBJECT IDENTIFIER
    ::= { cevModuleN3KType 5 }

-- Nexus 3000 Series 1 RU fixed module with  48 SFP+ and 4 QSFP ports

cevN3kC3548P10GFixedModule  OBJECT IDENTIFIER
    ::= { cevModuleN3KType 6 }

-- Nexus 3500 Series 1 RU fixed module with 48 SFP ports

cevN3kC3064TQ10GTFixedModule  OBJECT IDENTIFIER
    ::= { cevModuleN3KType 7 }

-- Nexus 3000 Series 1 RU fixed module with  48 SFP+ and 4 QSFP ports

cevN3KC3172  OBJECT IDENTIFIER
    ::= { cevModuleN3KType 8 }

-- N3K / QuickIron2 Supervisor module

cevN3KC3172TQ  OBJECT IDENTIFIER
    ::= { cevModuleN3KType 9 }

-- N3K / QuickZinc2 Supervisor module

cevN3KC3132TQ  OBJECT IDENTIFIER
    ::= { cevModuleN3KType 10 }

-- N3K / Neptune Supervisor module

cevN3KC3132CR  OBJECT IDENTIFIER
    ::= { cevModuleN3KType 11 }

-- N3K Neptune-CR Module Supervisor

cevModuleCGSType  OBJECT IDENTIFIER
    ::= { cevModule 86 }

-- cevModuleCGSType Modules

cevModuleCGS252016S8PC  OBJECT IDENTIFIER
    ::= { cevModuleCGSType 1 }

-- Cisco Connected Grid 2520 Switch, 16 100 SFP + 8 10/100 POE + 2 T/SFP Ethernet Interfaces

cevModuleCGS252024TC  OBJECT IDENTIFIER
    ::= { cevModuleCGSType 2 }

-- Cisco Connected Grid 2520 Switch, 24 10/100 + 2 T/SFP Ethernet Interfaces

cevModuleASR900Type  OBJECT IDENTIFIER
    ::= { cevModule 87 }

-- These are modules that are used in Cisco Aggregation Services Router 900 Series

cevModuleASR903RSP1A  OBJECT IDENTIFIER
    ::= { cevModuleASR900Type 1 }

-- ASR 903 Route Switch Processor 1, Base Scale, 55Gbps

cevModuleASR900ESP  OBJECT IDENTIFIER
    ::= { cevModuleASR900Type 2 }

-- Cisco ASR 900 Embedded Services Processor Module

cevModuleASR903RSP1B  OBJECT IDENTIFIER
    ::= { cevModuleASR900Type 3 }

-- ASR 903 Route Switch Processor 1, Large Scale, 55Gbps

cevModuleASR5000Type  OBJECT IDENTIFIER
    ::= { cevModule 88 }

-- cevModuleASR5000Type cards

cevModuleASR5K01100eK9  OBJECT IDENTIFIER
    ::= { cevModuleASR5000Type 1 }

-- FELC Ethernet 10/100 Line Card

cevModuleASR5K0110gMmK9  OBJECT IDENTIFIER
    ::= { cevModuleASR5000Type 2 }

-- XGLC 1-Port 10 Gigabit Ethernet Line Card w/MM SFP+

cevModuleASR5K0110gSmK9  OBJECT IDENTIFIER
    ::= { cevModuleASR5000Type 3 }

-- XGLC 1-Port 10 Gigabit Ethernet Line Card w/SM SFP+

cevModuleASR5K011G2LxK9  OBJECT IDENTIFIER
    ::= { cevModuleASR5000Type 4 }

-- GLC2 1-Port 1xGbE Line Card - 2nd Gen w/LX SM SFP

cevModuleASR5K011G2SxK9  OBJECT IDENTIFIER
    ::= { cevModuleASR5000Type 5 }

-- GLC2 1-Port 1xGbE Line Card - 2nd Gen w/SX MM SFP

cevModuleASR5K011G2TK9  OBJECT IDENTIFIER
    ::= { cevModuleASR5000Type 6 }

-- GLC2 1-Port 1xGbE Line Card - 2nd Gen w/Copper SFP

cevModuleASR5K011GELxK9  OBJECT IDENTIFIER
    ::= { cevModuleASR5000Type 7 }

-- GELC Ethernet 1000 Line Card w/LX Single-Mode SFP

cevModuleASR5K011GESxK9  OBJECT IDENTIFIER
    ::= { cevModuleASR5000Type 8 }

-- GELC Ethernet 1000 Line Card w/SX Multi-Mode Short Haul SFP

cevModuleASR5K011GETK9  OBJECT IDENTIFIER
    ::= { cevModuleASR5000Type 9 }

-- GELC Ethernet 1000 Line Card w/Copper SFP

cevModuleASR5K01OC3MmK9  OBJECT IDENTIFIER
    ::= { cevModuleASR5000Type 10 }

-- ATM/POS OC-3 with Multi-Mode Fiber SFP

cevModuleASR5K01OC3SmK9  OBJECT IDENTIFIER
    ::= { cevModuleASR5000Type 11 }

-- ATM/POS OC-3 with Single-Mode Fiber SFP

cevModuleASR5K041GeLxK9  OBJECT IDENTIFIER
    ::= { cevModuleASR5000Type 12 }

-- QGLC 4-Port Ethernet 1000 Line Card w/LX SM Long Haul SFP

cevModuleASR5K041GeSxK9  OBJECT IDENTIFIER
    ::= { cevModuleASR5000Type 13 }

-- QGLC 4-Port Ethernet 1000 Line Card w/SX MM Short Haul SFP

cevModuleASR5K041GeTK9  OBJECT IDENTIFIER
    ::= { cevModuleASR5000Type 14 }

-- QGLC 4-Port Ethernet 1000 Line Card w/Copper SFP

cevModuleASR5K042GeLxK9  OBJECT IDENTIFIER
    ::= { cevModuleASR5000Type 15 }

-- QGLC Rev2 4-Port Ethernet 1000 LC w/LX SM Long Haul SFP

cevModuleASR5K042GeSxK9  OBJECT IDENTIFIER
    ::= { cevModuleASR5000Type 16 }

-- QGLC Rev2 4-Port Ethernet 1000 LC w/SX MM Short Haul SFP

cevModuleASR5K042GeTK9  OBJECT IDENTIFIER
    ::= { cevModuleASR5000Type 17 }

-- QGLC Rev2 4-Port Ethernet 1000 Line Card w/Copper SFP

cevModuleASR5K08100eK9  OBJECT IDENTIFIER
    ::= { cevModuleASR5000Type 18 }

-- FLC2 8-Port Ethernet 10/100, 2nd Generation

cevModuleASR5K4OC3CMmK9  OBJECT IDENTIFIER
    ::= { cevModuleASR5000Type 19 }

-- OLC2 4 Port ATM STM-1c/OC-3c w/Multi-Mode SFP

cevModuleASR5K4OC3CSmK9  OBJECT IDENTIFIER
    ::= { cevModuleASR5000Type 20 }

-- OLC2 4 Port ATM STM-1c/OC-3c w/Single Mode SFP

cevModuleASR5KC1OC3MnK9  OBJECT IDENTIFIER
    ::= { cevModuleASR5000Type 21 }

-- Channelized 1-Port STM-1/OC-3 MM SFP Line Card

cevModuleASR5KC1OC3SmK9  OBJECT IDENTIFIER
    ::= { cevModuleASR5000Type 22 }

-- Channelized 1-Port STM-1/OC-3 SM SFP Line Card

cevModuleASR5KC4OC3MmK9  OBJECT IDENTIFIER
    ::= { cevModuleASR5000Type 23 }

-- CLC2 Channelized 4-Port STM-1/OC-3 Line Card w/MM SFP

cevModuleASR5KC4OC3SmK9  OBJECT IDENTIFIER
    ::= { cevModuleASR5000Type 24 }

-- CLC2 Channelized 4-Port STM-1/OC-3 Line Card w/SM SFP

cevModuleASR5KppcK9  OBJECT IDENTIFIER
    ::= { cevModuleASR5000Type 25 }

-- Packet Processing Card (PPC) 16GB

cevModuleASR5Kpsc16gK9  OBJECT IDENTIFIER
    ::= { cevModuleASR5000Type 26 }

-- Packet Services Card (PSC-A) 16GBppf

cevModuleASR5Kpsc32gK9  OBJECT IDENTIFIER
    ::= { cevModuleASR5000Type 27 }

-- Packet Services Card (PSC2) 32GB

cevModuleASR5Kpsc64gK9  OBJECT IDENTIFIER
    ::= { cevModuleASR5000Type 28 }

-- Packet Services Card (PSC3) 64GB

cevModuleASR5KpscK9  OBJECT IDENTIFIER
    ::= { cevModuleASR5000Type 29 }

-- Packet Services Card (PSC) 16GB

cevModuleASR5KsmcK9  OBJECT IDENTIFIER
    ::= { cevModuleASR5000Type 30 }

-- System Management Card 4GB

cevModuleASR5KSps3BncK9  OBJECT IDENTIFIER
    ::= { cevModuleASR5000Type 31 }

-- Switch Processor I/O, BNC BITS with Stratum 3

cevModuleASR5KSps33pnK9  OBJECT IDENTIFIER
    ::= { cevModuleASR5000Type 32 }

-- Switch Processor I/O, 3-Pin BITS with Stratum 3

cevModuleASR5KSpioBncK9  OBJECT IDENTIFIER
    ::= { cevModuleASR5000Type 33 }

-- Switch Processor I/O, BNC BITS

cevModuleASR5KSpio3pnK9  OBJECT IDENTIFIER
    ::= { cevModuleASR5000Type 34 }

-- Switch Processor I/O, 3-Pin BITS

cevModuleASR5KRccK9  OBJECT IDENTIFIER
    ::= { cevModuleASR5000Type 35 }

-- Redundancy Crossbar Card

cevModuleASR5500Type  OBJECT IDENTIFIER
    ::= { cevModule 89 }

-- cevModuleASR5500Type cards

cevModuleASR55DPC  OBJECT IDENTIFIER
    ::= { cevModuleASR5500Type 1 }

-- ASR5500 Data Processing Card (DPC)

cevModuleASR55FSC  OBJECT IDENTIFIER
    ::= { cevModuleASR5500Type 2 }

-- ASR5500 Fabric and Storage Card (FSC)

cevModuleASR55MIO10GL10  OBJECT IDENTIFIER
    ::= { cevModuleASR5500Type 3 }

-- ASR5500 Management and I/O (MIO) Card, 10 x 10GBASE-LR

cevModuleASR55MIO10GL20  OBJECT IDENTIFIER
    ::= { cevModuleASR5500Type 4 }

-- ASR5500 Management and I/O (MIO) Card, 20 x 10GBASE-LR

cevModuleASR55MIO10GS10  OBJECT IDENTIFIER
    ::= { cevModuleASR5500Type 5 }

-- ASR5500 Management and I/O (MIO) Card, 10 x 10GBASE-SR

cevModuleASR55MIO10GS20  OBJECT IDENTIFIER
    ::= { cevModuleASR5500Type 6 }

-- ASR5500 Management and I/O (MIO) Card, 20 x 10GBASE-SR

cevModuleASR55MIOBASE  OBJECT IDENTIFIER
    ::= { cevModuleASR5500Type 7 }

-- ASR5500 Management and I/O (MIO) Base Card, 20 Port, No SFPs

cevModuleASR55SSC  OBJECT IDENTIFIER
    ::= { cevModuleASR5500Type 8 }

-- ASR5500 System Status Card (SSC)

cevModuleVSR1000Type  OBJECT IDENTIFIER
    ::= { cevModule 90 }

-- These are modules that are used in Cisco Virtual Services Router 1000

cevModuleVSR1000RP  OBJECT IDENTIFIER
    ::= { cevModuleVSR1000Type 1 }

-- Cisco VSR 1000 Routing Processor Module

cevModuleVSR1000ESP  OBJECT IDENTIFIER
    ::= { cevModuleVSR1000Type 2 }

-- Cisco VSR 1000 Embedded Services Processor Module

cevModuleCgrType  OBJECT IDENTIFIER
    ::= { cevModule 91 }

-- cevModuleCgrType Modules

cevModuleCGMPlc  OBJECT IDENTIFIER
    ::= { cevModuleCgrType 18 }

-- Connected Grid Module - PLC Module

cevModuleCGMGe  OBJECT IDENTIFIER
    ::= { cevModuleCgrType 19 }

-- Connected Grid Module - Gigabit Ethernet

cevModuleCGM3gEVDOSE  OBJECT IDENTIFIER
    ::= { cevModuleCgrType 21 }

-- Connected Grid Module - 3G Sprint EV-DO Rev A/0/1xRTT Extended Temperature Range

cevModuleCGM3gEVDOVE  OBJECT IDENTIFIER
    ::= { cevModuleCgrType 22 }

-- Connected Grid Module - 3G Verizon EV-DO Rev A/0/1xRTT Extended Temperature Range

cevModuleCGM3gHSPAAE  OBJECT IDENTIFIER
    ::= { cevModuleCgrType 23 }

-- Connected Grid Module - 3G AT&T HSPA+/UMTS/GSM/GPRS/EDGE Extended Temperature Range

cevModuleCGM3gHSPAGE  OBJECT IDENTIFIER
    ::= { cevModuleCgrType 24 }

-- Connected Grid Module - 3G (Global) HSPA+/UMTS/GSM/GPRS/EDGE Extended Temperature Range

cevModuleCGM3gHspaAbGE  OBJECT IDENTIFIER
    ::= { cevModuleCgrType 25 }

-- Connected Grid Module - 3G (All Bands) HSPA+/UMTS/GSM/EDGE Extended Temperature Range

cevModuleISR4400Type  OBJECT IDENTIFIER
    ::= { cevModule 92 }

-- These are modules that are used in Cisco ISR 4400 Series Router

cevModuleISR4441RP  OBJECT IDENTIFIER
    ::= { cevModuleISR4400Type 1 }

-- Cisco ISR 4441 Routing Processor Module

cevModuleISR4442RP  OBJECT IDENTIFIER
    ::= { cevModuleISR4400Type 2 }

-- Cisco ISR 4442 Routing Processor Module

cevModuleISR4451RP  OBJECT IDENTIFIER
    ::= { cevModuleISR4400Type 3 }

-- Cisco ISR 4451 Routing Processor Module

cevModuleISR4452RP  OBJECT IDENTIFIER
    ::= { cevModuleISR4400Type 4 }

-- Cisco ISR 4452 Routing Processor Module

cevModuleISR4400RP  OBJECT IDENTIFIER
    ::= { cevModuleISR4400Type 5 }

-- Cisco ISR 4400 Series Routing Processor Module

cevModuleISR4441FP  OBJECT IDENTIFIER
    ::= { cevModuleISR4400Type 6 }

-- Cisco ISR 4441 Forwarding Processor Module

cevModuleISR4442FP  OBJECT IDENTIFIER
    ::= { cevModuleISR4400Type 7 }

-- Cisco ISR 4442 Forwarding Processor Module

cevModuleISR4451FP  OBJECT IDENTIFIER
    ::= { cevModuleISR4400Type 8 }

-- Cisco ISR 4451 Forwarding Processor Module

cevModuleISR4452FP  OBJECT IDENTIFIER
    ::= { cevModuleISR4400Type 9 }

-- Cisco ISR 4452 Forwarding Processor Module

cevModuleISR4400FP  OBJECT IDENTIFIER
    ::= { cevModuleISR4400Type 10 }

-- Cisco ISR 4400 Series Forwarding Processor Module

cevModuleISR4400NIM  OBJECT IDENTIFIER
    ::= { cevModuleISR4400Type 11 }

-- Cisco ISR 4400 Series Built-In Network Interface Module controller

cevModuleISR4441NIM  OBJECT IDENTIFIER
    ::= { cevModuleISR4400Type 12 }

-- Cisco ISR 4441 Built-In Network Interface Module  controller

cevModuleISR4442NIM  OBJECT IDENTIFIER
    ::= { cevModuleISR4400Type 13 }

-- Cisco ISR 4442 Built-In Network Interface Module  controller

cevModuleISR4451NIM  OBJECT IDENTIFIER
    ::= { cevModuleISR4400Type 14 }

-- Cisco ISR 4451 Built-In Network Interface Module  controller

cevModuleISR4452NIM  OBJECT IDENTIFIER
    ::= { cevModuleISR4400Type 15 }

-- Cisco ISR 4452 Built-In Network Interface Module  controller

cevModuleISR4400ESM  OBJECT IDENTIFIER
    ::= { cevModuleISR4400Type 16 }

-- Cisco ISR 4400 Series Built-In Enhanced Service Module controller Module

cevModuleISR4441ESM  OBJECT IDENTIFIER
    ::= { cevModuleISR4400Type 17 }

-- Cisco ISR 4441 Built-In Enhanced Service Module controller Module

cevModuleISR4442ESM  OBJECT IDENTIFIER
    ::= { cevModuleISR4400Type 18 }

-- Cisco ISR 4442 Built-In Enhanced Service Module controller Module

cevModuleISR4451ESM  OBJECT IDENTIFIER
    ::= { cevModuleISR4400Type 19 }

-- Cisco ISR 4451 Built-In Enhanced Service Module controller Module

cevModuleISR4452ESM  OBJECT IDENTIFIER
    ::= { cevModuleISR4400Type 20 }

-- Cisco ISR 4452 Built-In Enhanced Service Module controller Module

cevModuleISR44000FP4xGE  OBJECT IDENTIFIER
    ::= { cevModuleISR4400Type 21 }

-- Cisco ISR 4400 Series Built-in Front Panel 4xGE Module

cevModuleISR4400InternalPOE  OBJECT IDENTIFIER
    ::= { cevModuleISR4400Type 22 }

-- Cisco ISR 4400 Series Internal Power Over Ethernet Card for Onboard GE

cevModuleNGWICSerial1T  OBJECT IDENTIFIER
    ::= { cevModuleISR4400Type 43 }

-- 1-Port 12in1 serial network interface module

cevModuleNGWICSerial2T  OBJECT IDENTIFIER
    ::= { cevModuleISR4400Type 44 }

-- 2-Port 12in1 serial network interface module

cevModuleNGWICSerial4T  OBJECT IDENTIFIER
    ::= { cevModuleISR4400Type 45 }

-- 4-Port 12in1 serial network interface module

cevModuleQSFPPlusS  OBJECT IDENTIFIER
    ::= { cevModule 93 }

-- group for QSFP+ Modules

cevQSFP40GLR4  OBJECT IDENTIFIER
    ::= { cevModuleQSFPPlusS 1 }

-- 40G-LR4 QSFP+ Module for SMF

cevQSFP40GSR4  OBJECT IDENTIFIER
    ::= { cevModuleQSFPPlusS 2 }

-- 40G-SR4 QSFP+ Module for MMF

cevQSFP40GSMSR4  OBJECT IDENTIFIER
    ::= { cevModuleQSFPPlusS 3 }

-- 40G-SMSR4 QSFP+ Module for SMF ans MMF

cevQSFP40GCR4Active  OBJECT IDENTIFIER
    ::= { cevModuleQSFPPlusS 4 }

-- 40G-CR4Active QSFP+ Module for Copper Active

cevQSFP40GCR4Passive  OBJECT IDENTIFIER
    ::= { cevModuleQSFPPlusS 5 }

-- 40G-CR4Passive QSFP+ Module for Copper Passive

cevModuleN6KType  OBJECT IDENTIFIER
    ::= { cevModule 95 }

-- Module for Nexus 6004

cevN6KC6004M20UP  OBJECT IDENTIFIER
    ::= { cevModuleN6KType 1 }

-- Nexus 6004 Unified Module 20 Ports 10GE Eth/FCoE OR 16/8/4/2G FC

cevN6KC6004M12Q  OBJECT IDENTIFIER
    ::= { cevModuleN6KType 2 }

-- Nexus 6004 Module 12Q 40GE Ethernet/FCoE

cevN6KC600496QFixedModule  OBJECT IDENTIFIER
    ::= { cevModuleN6KType 3 }

-- The fixed module that has 48Q 40GE ports + supervisor in Nexus 6004

cevN6KC6001M4Q  OBJECT IDENTIFIER
    ::= { cevModuleN6KType 4 }

-- Nexus 6001 4xQSFP Module

cevN6KC600164PFixedModule  OBJECT IDENTIFIER
    ::= { cevModuleN6KType 5 }

-- The fixed module that has 48 10GE Ethernet/FCoE ports + supervisor in Nexus 6001

cevN6KC600164TFixedModule  OBJECT IDENTIFIER
    ::= { cevModuleN6KType 11 }

-- The fixed module that has 48x10G-BaseT ports + supervisor in Nexus 6001

cevN6KN6004M12Q  OBJECT IDENTIFIER
    ::= { cevModuleN6KType 18 }

-- Nexus 6004 Module 12Q 40GE Ethernet/FCoE

cevN6KC6001M6Q  OBJECT IDENTIFIER
    ::= { cevModuleN6KType 19 }

-- N6001 6xQSFP Module

cevModuleISRType  OBJECT IDENTIFIER
    ::= { cevModule 96 }

-- These are modules that are used in Cisco ISR Series Router

cevModuleISRSM1T3E3  OBJECT IDENTIFIER
    ::= { cevModuleISRType 1 }

-- Cisco ISR SM-1 T3/E3 Module

cevModuleISRSM6XGE  OBJECT IDENTIFIER
    ::= { cevModuleISRType 2 }

-- 6 Port Gige Service Module for ISR

cevModuleISRSM1X10GE4XGE  OBJECT IDENTIFIER
    ::= { cevModuleISRType 3 }

-- 1 Port TenGig and 4 Port Gige Service Module for ISR

cevModuleISRSmEs3x16P  OBJECT IDENTIFIER
    ::= { cevModuleISRType 4 }

-- EtherSwitch Next Generation Service Module Layer3 + MACSec + PoEPlus + 16 10/100/1000

cevModuleISRSmEs3x24P  OBJECT IDENTIFIER
    ::= { cevModuleISRType 5 }

-- EtherSwitch Next Generation Service Module Layer3 + MACSec + PoEPlus + 24 10/100/1000

cevModuleISRSmDEs3x48P  OBJECT IDENTIFIER
    ::= { cevModuleISRType 6 }

-- EtherSwitch Double Wide Next Generation Service Module Layer3 + MACSec + PoEPlus + 48 10/100/1000

cevModuleN77Type  OBJECT IDENTIFIER
    ::= { cevModule 97 }

-- Group for the Nexus7700 type of cards

cevN77c7718Fab2  OBJECT IDENTIFIER
    ::= { cevModuleN77Type 1 }

-- Fabric for Nexus7700 18-slot chassis

cevN77c7710Fab2  OBJECT IDENTIFIER
    ::= { cevModuleN77Type 2 }

-- Fabric for Nexus7700 10-slot chassis

cevN77F248XP23E  OBJECT IDENTIFIER
    ::= { cevModuleN77Type 4 }

-- N77-F248XP-23E Enhanced 1/10 Gbps Ethernet Module

cevN77SUP2E  OBJECT IDENTIFIER
    ::= { cevModuleN77Type 5 }

-- N77-SUP2E Nexus 7700 Supervisor

cevModuleCat3KCAxType  OBJECT IDENTIFIER
    ::= { cevModule 98 }

-- These cards are used in the Cisco catalyst converged access switches

cevModule57xxwlc  OBJECT IDENTIFIER
    ::= { cevModule 99 }

-- These cards are used in Cisco next gen Wireless Controller

cevModuleN95KType  OBJECT IDENTIFIER
    ::= { cevModule 100 }

-- These cards are used for Nexus 9500 series

cevN9KSUPA  OBJECT IDENTIFIER
    ::= { cevModuleN95KType 1 }

-- N9K-SUP-A Supervisor Module for Nexus 9500 series

cevN9Kc9508FM  OBJECT IDENTIFIER
    ::= { cevModuleN95KType 2 }

-- N9K-C9508-FM Fabric Module for Nexus 9508 chassis

cevN9kScA  OBJECT IDENTIFIER
    ::= { cevModuleN95KType 3 }

-- N9K-SC-A System Controller Module for Nexus 9500 series chassis

cevN9kX9564PX  OBJECT IDENTIFIER
    ::= { cevModuleN95KType 4 }

-- N9K-X9564PX 48 port 1/10G SFP+ plus 4 port QSFP Ethernet  Module for Nexus 9500 series chassis

cevN9kX9564TX  OBJECT IDENTIFIER
    ::= { cevModuleN95KType 5 }

-- N9K-X9564TX 48 port 1/10G-BaseT plus 4 port QSFP Ethernet  Module for Nexus 9500 series chassis

cevN9kX9636PQ  OBJECT IDENTIFIER
    ::= { cevModuleN95KType 6 }

-- N9K-X9636PQ 36p 40G QSFP Ethernet Module for Nexus 9500 series chassis

cevN9KM12PQ  OBJECT IDENTIFIER
    ::= { cevModuleN95KType 7 }

-- GEM card, 12x40G QSFP

cevModuleCPAKType  OBJECT IDENTIFIER
    ::= { cevModule 101 }

-- Group for 100G CPAK modules

cevDirectAttachCable40Gs  OBJECT IDENTIFIER
    ::= { cevModule 102 }

-- Group for DirectAttachCable40Gs Type of Cards

cevQSFP4SFP10GCU1M  OBJECT IDENTIFIER
    ::= { cevDirectAttachCable40Gs 1 }

-- QSFP to 4xSFP10G Passive Copper Splitter Cable, 1m

cevQSFP4SFP10GCU3M  OBJECT IDENTIFIER
    ::= { cevDirectAttachCable40Gs 2 }

-- QSFP to 4xSFP10G Passive Copper Splitter Cable, 3m

cevQSFP4SFP10GCU5M  OBJECT IDENTIFIER
    ::= { cevDirectAttachCable40Gs 3 }

-- QSFP to 4xSFP10G Passive Copper Splitter Cable, 5m

cevModuleN93KType  OBJECT IDENTIFIER
    ::= { cevModule 103 }

-- These cards are used for Nexus 9300 series

cevN93KM6PQ  OBJECT IDENTIFIER
    ::= { cevModuleN93KType 1 }

-- 6x40G QSFP GEM Card for Nexus 9300 TOR platform

cevN93KM12PQ  OBJECT IDENTIFIER
    ::= { cevModuleN93KType 2 }

-- 12x40G QSFP GEM Card for Nexus 9300 TOR platform

cevPort  OBJECT IDENTIFIER
    ::= { cevMIBObjects 10 }

cevPortUnknown  OBJECT IDENTIFIER
    ::= { cevPort 1 }

cevPortMCIEther  OBJECT IDENTIFIER
    ::= { cevPort 2 }

-- MCI Ethernet

cevPortMCISerial  OBJECT IDENTIFIER
    ::= { cevPort 3 }

-- MCI HDLC

cevPortCBusSerial  OBJECT IDENTIFIER
    ::= { cevPort 4 }

cevPortFddi  OBJECT IDENTIFIER
    ::= { cevPort 5 }

-- CBus FCI (v1)

cevPortFddit  OBJECT IDENTIFIER
    ::= { cevPort 6 }

-- CBus FCI-T

cevPortCBusTR  OBJECT IDENTIFIER
    ::= { cevPort 7 }

-- CBus Token Ring

cevPortAsync  OBJECT IDENTIFIER
    ::= { cevPort 8 }

-- random async line

cevPortHSSI  OBJECT IDENTIFIER
    ::= { cevPort 9 }

-- High Speed Serial (T3)

cevPortT1  OBJECT IDENTIFIER
    ::= { cevPort 10 }

-- card with T1 interface

cevPortE1  OBJECT IDENTIFIER
    ::= { cevPort 11 }

-- E1 interface

cevPortBRI  OBJECT IDENTIFIER
    ::= { cevPort 12 }

-- BRI interface

cevPortAIP  OBJECT IDENTIFIER
    ::= { cevPort 13 }

-- h/w is ATM Interface Processor

cevPortCIP  OBJECT IDENTIFIER
    ::= { cevPort 14 }

-- h/w is Channel Interface Processor Deprecated

cevPortVtyAsync  OBJECT IDENTIFIER
    ::= { cevPort 15 }

-- random virtual async line

cevPortFEIP  OBJECT IDENTIFIER
    ::= { cevPort 16 }

-- Fast Ethernet Interface Processor

cevPortAsyncGroup  OBJECT IDENTIFIER
    ::= { cevPort 17 }

-- master async line

cevPortVTemplate  OBJECT IDENTIFIER
    ::= { cevPort 18 }

-- virtual template interface

cevPortVAccess  OBJECT IDENTIFIER
    ::= { cevPort 19 }

-- virtual access interface

cevPortT3  OBJECT IDENTIFIER
    ::= { cevPort 20 }

-- T3 interface

cevPortVGAnyLAN  OBJECT IDENTIFIER
    ::= { cevPort 21 }

-- 1000VG-AnyLAN

cevPortLance  OBJECT IDENTIFIER
    ::= { cevPort 22 }

-- h/w is AMD Lance Ethernet

cevPortATMS2000  OBJECT IDENTIFIER
    ::= { cevPort 23 }

-- ATMS2000 ATM switch chip set

cevPortSALI25  OBJECT IDENTIFIER
    ::= { cevPort 24 }

-- Transwitch SALI 25Mbps ATM

cevPortSonicT  OBJECT IDENTIFIER
    ::= { cevPort 25 }

-- Nat'l SonicT

cevPortOC3SUNI  OBJECT IDENTIFIER
    ::= { cevPort 26 }

-- PMC Sierra PM5346

cevPortOC12SUNI  OBJECT IDENTIFIER
    ::= { cevPort 27 }

-- PMC Sierra PM5355

cevPortDS3SUNI  OBJECT IDENTIFIER
    ::= { cevPort 28 }

-- PMC Sierra PM7345 - DS3 mode

cevPortE3SUNI  OBJECT IDENTIFIER
    ::= { cevPort 29 }

-- PMC Sierra PM7345 - E3 mode

cevPortDS3SUNIQUAD  OBJECT IDENTIFIER
    ::= { cevPort 30 }

-- PMC Sierra PM7345 - DS3 mode

cevPortE3SUNIQUAD  OBJECT IDENTIFIER
    ::= { cevPort 31 }

-- PMC Sierra PM7345 - E3 mode

cevPortMK5025  OBJECT IDENTIFIER
    ::= { cevPort 32 }

-- MK5025 Serial

cevPortTMS380  OBJECT IDENTIFIER
    ::= { cevPort 33 }

-- TMS380 Tokenring

cevPortBSI  OBJECT IDENTIFIER
    ::= { cevPort 34 }

-- Nat'l BSI DP83200 fddi

cevPortATMZR  OBJECT IDENTIFIER
    ::= { cevPort 35 }

-- LSI Logic ATMizer

cevPortHD64570  OBJECT IDENTIFIER
    ::= { cevPort 36 }

-- HD 64570 Serial

cevPortPCBus  OBJECT IDENTIFIER
    ::= { cevPort 37 }

-- PC (ISA) Bus

cevPortQuiccEther  OBJECT IDENTIFIER
    ::= { cevPort 38 }

cevPortQuiccSerial  OBJECT IDENTIFIER
    ::= { cevPort 39 }

cevPortAMDP2  OBJECT IDENTIFIER
    ::= { cevPort 40 }

-- AMD Presidio2 Ethernet

cevPortMIF68840  OBJECT IDENTIFIER
    ::= { cevPort 41 }

-- Motorola MIF68840 Fddi

cevPortCYLEPA  OBJECT IDENTIFIER
    ::= { cevPort 42 }

-- Cylink Encryption Card

cevPortS4T68360  OBJECT IDENTIFIER
    ::= { cevPort 43 }

-- 68360 Serial

cevPortIBM2692  OBJECT IDENTIFIER
    ::= { cevPort 44 }

-- ibm 2692 token ring

cevPortMueslix  OBJECT IDENTIFIER
    ::= { cevPort 45 }

-- Mueslix link Serial

cevPortCD2430  OBJECT IDENTIFIER
    ::= { cevPort 46 }

-- CD2430 Serial

cevPortILACC  OBJECT IDENTIFIER
    ::= { cevPort 47 }

-- AMD 79900 Ethernet

cevPortNIC100  OBJECT IDENTIFIER
    ::= { cevPort 48 }

-- GrandJunction FastNIC100 Ethernet

cevPortDCUATM  OBJECT IDENTIFIER
    ::= { cevPort 49 }

-- Cisco DCU, PMC Framer

cevPortDCUATMPort  OBJECT IDENTIFIER
    ::= { cevPort 50 }

-- Cisco DCU, PMC Framer

cevPortTI1570  OBJECT IDENTIFIER
    ::= { cevPort 51 }

-- Texas Instruments 1570 ATM

cevPortPOS  OBJECT IDENTIFIER
    ::= { cevPort 52 }

-- Packet Over Sonet

cevPortLoopBack  OBJECT IDENTIFIER
    ::= { cevPort 53 }

-- hardware is loopback

cevPortLex  OBJECT IDENTIFIER
    ::= { cevPort 54 }

-- Lan Extension interface

cevPortDialer  OBJECT IDENTIFIER
    ::= { cevPort 55 }

-- Dialer interface

cevPortCIPLANAdapter  OBJECT IDENTIFIER
    ::= { cevPort 56 }

-- CIP internal LAN adapter

cevPortBVI  OBJECT IDENTIFIER
    ::= { cevPort 57 }

-- Bridge-group Virtual Interface

cevPortOSPFVL  OBJECT IDENTIFIER
    ::= { cevPort 58 }

-- OSPF Virtual Link interface

cevPortRinconSwitch  OBJECT IDENTIFIER
    ::= { cevPort 59 }

-- RINCON Frame Relay switch virtual interface

cevPortSynALCATM  OBJECT IDENTIFIER
    ::= { cevPort 60 }

-- Synergy ATM Line Card ATM interface

cevPortSynALCBIGA  OBJECT IDENTIFIER
    ::= { cevPort 61 }

-- Synergy ATM Line Card in-band IPC interface

cevPortSwitchTrunk  OBJECT IDENTIFIER
    ::= { cevPort 62 }

-- Rincon switch trunk (e.g. FTC)

cevPortC2KATM  OBJECT IDENTIFIER
    ::= { cevPort 63 }

-- SIBU ATM line card for 2800 switch

cevPortDec21140A  OBJECT IDENTIFIER
    ::= { cevPort 64 }

-- Dec 21140A Fast Ethernet Interface

cevPortC5Ether  OBJECT IDENTIFIER
    ::= { cevPort 65 }

-- Yosemite, pseudo ethernet

cevPortC5TR  OBJECT IDENTIFIER
    ::= { cevPort 66 }

-- Yosemite, pseudo token ring

cevPortEswitch  OBJECT IDENTIFIER
    ::= { cevPort 69 }

-- c7200 Ethernet Switch Port Adapter

cevPortBITS  OBJECT IDENTIFIER
    ::= { cevPort 70 }

-- BITS (Building Integrated Timing Supply) port for telco network clock & alarm handling card for Cat8540

cevPortAdslCap  OBJECT IDENTIFIER
    ::= { cevPort 71 }

-- ADSL CAP Line

cevPortAdslDmt  OBJECT IDENTIFIER
    ::= { cevPort 72 }

-- ADSL DMT Line

cevPortSdsl2b1q  OBJECT IDENTIFIER
    ::= { cevPort 73 }

-- SDSL 2B1Q line

cevPortEscon  OBJECT IDENTIFIER
    ::= { cevPort 74 }

-- IBM ESCON interface type for CIP or CIP2 cards/port adapters

cevPortParallel  OBJECT IDENTIFIER
    ::= { cevPort 75 }

-- IBM Parallel (Bus & Tag) interface type for CIP or CIP2 cards/port adapters

cevPortCipVirtual  OBJECT IDENTIFIER
    ::= { cevPort 76 }

-- Virtual port on a CIP or CIP2 card

cevPortDs3  OBJECT IDENTIFIER
    ::= { cevPort 78 }

-- DS-3 interface

cevPortE3  OBJECT IDENTIFIER
    ::= { cevPort 79 }

-- E-3 interface

cevPortOc3  OBJECT IDENTIFIER
    ::= { cevPort 80 }

-- OC-3 interface

cevPortHdvDsp  OBJECT IDENTIFIER
    ::= { cevPort 82 }

-- DSP processor port on the cevDspmPvdm3 daughtercard

cevPortAdslFlexiDmt  OBJECT IDENTIFIER
    ::= { cevPort 83 }

-- Flexi DMT port

cevPortAdslFlexiCap  OBJECT IDENTIFIER
    ::= { cevPort 84 }

-- Flexi CAP port

cevPortAdslDmtIsdn  OBJECT IDENTIFIER
    ::= { cevPort 85 }

-- DMT over ISDN port

cevPortRfMac  OBJECT IDENTIFIER
    ::= { cevPort 86 }

-- Line card RF Mac layer for UBR7200

cevPortRfUs  OBJECT IDENTIFIER
    ::= { cevPort 87 }

-- Line card upstream interface for UBR7200

cevPortRfDs  OBJECT IDENTIFIER
    ::= { cevPort 88 }

-- Line card downstream interface for UBR7200

cevPortUbrClk  OBJECT IDENTIFIER
    ::= { cevPort 89 }

-- Cable national clock card DB-15 interface

cevPortShdslTcpam  OBJECT IDENTIFIER
    ::= { cevPort 90 }

-- Single-Pair High-bit-rate DSL Trellis-Coded PAM Line

cevPortShdslTcpamOptis  OBJECT IDENTIFIER
    ::= { cevPort 91 }

-- Single-Pair High-bit-rate DSL Trellis-Coded PAM Overlapped PAM Transmission with Interlocking Spectra (OPTIS) Line

cevPortGEIP  OBJECT IDENTIFIER
    ::= { cevPort 100 }

-- Gigabit Ethernet interface processor

cevPortWDM  OBJECT IDENTIFIER
    ::= { cevPort 101 }

-- Passive optical trunk port that sends and receives multiple wavelengths on the ITU grid

cevPortThru  OBJECT IDENTIFIER
    ::= { cevPort 102 }

-- Optical port carrying passed-through wavelengths

cevPortFilter  OBJECT IDENTIFIER
    ::= { cevPort 103 }

-- Passive optical port on a mux/demux module carrying one ITU DWDM grid wavelength to or from the multiplexed signal

cevPortWave  OBJECT IDENTIFIER
    ::= { cevPort 104 }

-- Optical port transmitting and receiving one ITU DWDM grid wavelength

cevPortWavePatch  OBJECT IDENTIFIER
    ::= { cevPort 105 }

-- Passive optical port connecting the port that transmits and receives ITU DWDM grid wavelength with the mux/demux port that carries it

cevPortTransparent  OBJECT IDENTIFIER
    ::= { cevPort 106 }

-- Optical port that handles multiple protocols (ESCON, FICON, etc.)

cevPortDPT  OBJECT IDENTIFIER
    ::= { cevPort 107 }

-- Dynamic Packet Transport (DPT) Interface

cevPortOc12  OBJECT IDENTIFIER
    ::= { cevPort 108 }

-- OC-12 interface

cevPortGe  OBJECT IDENTIFIER
    ::= { cevPort 109 }

-- Gigabit Ethernet Port

cevPortChOc12  OBJECT IDENTIFIER
    ::= { cevPort 110 }

-- Channelized OC12 Port

cevPortChOc3Stm1  OBJECT IDENTIFIER
    ::= { cevPort 111 }

-- Channelized OC3/STM-1 Port

cevPortFilterGroup  OBJECT IDENTIFIER
    ::= { cevPort 112 }

-- Passive optical port that sends and receives multiple wavelengths on the ITU grid

cevPortFilterBand  OBJECT IDENTIFIER
    ::= { cevPort 113 }

-- Optical port carrying passed-through wavelengths

cevPortChE1T1  OBJECT IDENTIFIER
    ::= { cevPort 114 }

-- Channelized E1/T1 port

cevPortASIMod  OBJECT IDENTIFIER
    ::= { cevPort 115 }

-- Asynchronous Serial Interface Media Line Card Mac Layer for Cable Modem Termination System

cevPortASIIn  OBJECT IDENTIFIER
    ::= { cevPort 116 }

-- Media Line Card Asynchronous Serial Interface Input interface

cevPortASIOut  OBJECT IDENTIFIER
    ::= { cevPort 117 }

-- Media Line Card Asynchronous Serial Interface Output interface

cevPortAimDsp  OBJECT IDENTIFIER
    ::= { cevPort 118 }

-- DSP processor on AIM DSP modules

cevPortAtm  OBJECT IDENTIFIER
    ::= { cevPort 119 }

-- ATM interfaces

cevPortChSonet  OBJECT IDENTIFIER
    ::= { cevPort 120 }

-- channelized sonet interfaces

cevPortChOcX  OBJECT IDENTIFIER
    ::= { cevPort 121 }

-- channelized OC X card interfaces

cevPortFe  OBJECT IDENTIFIER
    ::= { cevPort 123 }

-- Fast ethernet interfaces

cevPortDs3E3Atm  OBJECT IDENTIFIER
    ::= { cevPort 125 }

-- DS3/E3 ATM interface

cevPortFxs  OBJECT IDENTIFIER
    ::= { cevPort 126 }

-- Foreign Exchange Station port

cevPortFxo  OBJECT IDENTIFIER
    ::= { cevPort 127 }

-- Foreign Exchange Office port

cevPortEM  OBJECT IDENTIFIER
    ::= { cevPort 128 }

-- Ear and Mouth interface port

cevPortOc48  OBJECT IDENTIFIER
    ::= { cevPort 129 }

-- OC-48 interface

cevPortOc192  OBJECT IDENTIFIER
    ::= { cevPort 130 }

-- OC-192 interface

cevPortFibreChannel  OBJECT IDENTIFIER
    ::= { cevPort 131 }

-- Fibre Channel interface

cevPortGigEthernet  OBJECT IDENTIFIER
    ::= { cevPort 132 }

-- Gigabit Ethernet interface

cevPortFibreChGigEth  OBJECT IDENTIFIER
    ::= { cevPort 133 }

-- Interface capable of handling Gigabit Ethernet or Fibre Channel Protocol

cevPortCatEthernet  OBJECT IDENTIFIER
    ::= { cevPort 134 }

-- Ethernet port for Catalyst 29xx/35xx series switch

cevPortWaveOsc  OBJECT IDENTIFIER
    ::= { cevPort 135 }

-- Optical port transmitting and receiving one ITU DWDM grid wavelength, used as the optical supervisory channel

cevPortWaveEthPhy  OBJECT IDENTIFIER
    ::= { cevPort 136 }

-- Optical port that transports ethernet packets in the ITU DWDM grid wavelength

cevPort10GigEthPhy  OBJECT IDENTIFIER
    ::= { cevPort 137 }

-- Optical port that transports 10 Gigabit Ethernet packets in the uncolored wavelength

cevPortEsconPhy  OBJECT IDENTIFIER
    ::= { cevPort 138 }

-- Optical port that is capable of transporting ESCON traffic

cevPortGEFCPhy  OBJECT IDENTIFIER
    ::= { cevPort 139 }

-- Optical port that is capable of transporting Gigabit Ethernet and Fibre Channel traffic

cevPortVOAIn  OBJECT IDENTIFIER
    ::= { cevPort 140 }

-- Input port on a Variable Optical Attenuator module

cevPortVOAOut  OBJECT IDENTIFIER
    ::= { cevPort 141 }

-- Output port on a Variable Optical Attenuator module

cevPortVOAFilterIn  OBJECT IDENTIFIER
    ::= { cevPort 142 }

-- Input port on an Optical Power Equaliser module that filters and attenuates a selective band of wavelengths

cevPortVOAFilterOut  OBJECT IDENTIFIER
    ::= { cevPort 143 }

-- Output port on an Optical Power Equaliser module that filters and attenuates a selective band of wavelengths

cevPortVOAByPassIn  OBJECT IDENTIFIER
    ::= { cevPort 144 }

-- Port on an Optical Power Equaliser module that accepts DWDM wavelengths that are not attenuated but are multiplexed with the attenuated wavelengths to form the output signal

cevPortVOAByPassOut  OBJECT IDENTIFIER
    ::= { cevPort 145 }

-- Port on an Optical Power Equaliser module that outputs those DWDM wavelengths in the input signal that are not being attenuated

cevPortGT96K  OBJECT IDENTIFIER
    ::= { cevPort 146 }

-- GT96K on board serial communication controller

cevPortDSCC4  OBJECT IDENTIFIER
    ::= { cevPort 147 }

-- DSCC4 serial communication controller present on the mowgli-board

cevPortBaseTEther  OBJECT IDENTIFIER
    ::= { cevPort 150 }

-- Ethernet 10/100/1000 BaseT port.

cevPortGESFP  OBJECT IDENTIFIER
    ::= { cevPort 151 }

-- Gigabit Ethernet Port Small Form factor Pluggable port.

cevPortWdmSplit  OBJECT IDENTIFIER
    ::= { cevPort 152 }

-- Passive optical trunk port that sends and receives multiple wavelengths in the ITU grid and is internally connected to an optical splitter

cevPortWavePassThru  OBJECT IDENTIFIER
    ::= { cevPort 153 }

-- Passive port transmitting and receiving optical signals, used to provide optical connectivity within the box and is incapable of monitoring or doing anything else with the signal

cevPortDspPVDM  OBJECT IDENTIFIER
    ::= { cevPort 154 }

-- DSP on a Packet Voice Data Module (PVDM) daughter card in 1700

cevPortiScsi  OBJECT IDENTIFIER
    ::= { cevPort 155 }

-- iSCSI port

cevPortVic2Did  OBJECT IDENTIFIER
    ::= { cevPort 156 }

-- Two port Direct Inward Dial trunk Voice Interface Card

cevPortWic1Adsl  OBJECT IDENTIFIER
    ::= { cevPort 157 }

-- 1-port ADSL WAN Interface Card

cevPortWic1Shdsl  OBJECT IDENTIFIER
    ::= { cevPort 158 }

-- 1-Port G.SHDSL WIC

cevPortWic1Ethernet  OBJECT IDENTIFIER
    ::= { cevPort 159 }

-- 1-port Ethernet WIC

cevPort10GigBaseEX4  OBJECT IDENTIFIER
    ::= { cevPort 160 }

-- 10 Gigabit Ethernet Wide-WDM 1550 Laser Xenpak Module

cevPort10GigBaseLR  OBJECT IDENTIFIER
    ::= { cevPort 161 }

-- 10 Gigabit Ethernet Serial 1310nm Laser Xenpak Module

cevPort10GigBaseSX4  OBJECT IDENTIFIER
    ::= { cevPort 162 }

-- 10 Gigabit Ethernet Wide-WDM 850nm Laser Xenpak Module

cevPort10GigBaseER  OBJECT IDENTIFIER
    ::= { cevPort 163 }

-- 10 Gigabit Ethernet Serial 1550nm Laser Xenpak Module

cevPortGigUnsupported  OBJECT IDENTIFIER
    ::= { cevPort 164 }

-- Unsupported Gbic Gigabit Ethernet

cevPortGigBaseZX  OBJECT IDENTIFIER
    ::= { cevPort 165 }

-- Extended Reach Gigabit Ethernet

cevPort10GigBaseCPX  OBJECT IDENTIFIER
    ::= { cevPort 166 }

-- 10 Gigabit Ethernet Parallel 860nm Laser Xenpak Module

cevPort10GigBaseLX4  OBJECT IDENTIFIER
    ::= { cevPort 167 }

-- 10 Gigabit Ethernet Wide-WDM 1310nm Laser Xenpak Module

cevPortGigBaseLX  OBJECT IDENTIFIER
    ::= { cevPort 168 }

-- Long Wave fiber Gigabit Ethernet

cevPortGigBaseSX  OBJECT IDENTIFIER
    ::= { cevPort 169 }

-- Short Wave fiber Gigabit Ethernet

cevPortGigBaseCX  OBJECT IDENTIFIER
    ::= { cevPort 170 }

-- Copper Gigabit Ethernet

cevPortGigBaseLH  OBJECT IDENTIFIER
    ::= { cevPort 171 }

-- Long Haul fiber Gigabit Ethernet

cevPortGigBaseT  OBJECT IDENTIFIER
    ::= { cevPort 172 }

-- Twisted Pair Gigabit Ethernet

cevPortDslsar  OBJECT IDENTIFIER
    ::= { cevPort 173 }

-- DSLSAR Controller used within xDSL cards in 1700,2600 and 3600 series router.

cevPortAtm25  OBJECT IDENTIFIER
    ::= { cevPort 174 }

-- 25Mbps ATM Interface.

cevPortAnalogFxs  OBJECT IDENTIFIER
    ::= { cevPort 175 }

-- Analog FXS Voice ports

cevPortE3Atm  OBJECT IDENTIFIER
    ::= { cevPort 176 }

-- E3 ATM interface

cevPortDs3Atm  OBJECT IDENTIFIER
    ::= { cevPort 177 }

-- DS3 ATM interface

cevPortNetworkAnalysis  OBJECT IDENTIFIER
    ::= { cevPort 178 }

-- Network Anaylsis interface

cevPortIntrusionDetect  OBJECT IDENTIFIER
    ::= { cevPort 180 }

-- Intrusion Detection interface

cevPort10GigBaseLW  OBJECT IDENTIFIER
    ::= { cevPort 181 }

-- 10 Gigabit Ethernet Serial 1310nm Laser Xenpak Module

cevPort10GigBaseEW  OBJECT IDENTIFIER
    ::= { cevPort 182 }

-- 10 Gigabit Ethernet Serial 1510nm Laser Xenpak Module

cevPortGigBaseUnknown  OBJECT IDENTIFIER
    ::= { cevPort 183 }

-- Unknown Giga Ethernet

cevPort10GigBaseUnknown  OBJECT IDENTIFIER
    ::= { cevPort 184 }

-- Unknown 10 Gigabit Ethernet

cevPort10GigBaseUnapproved  OBJECT IDENTIFIER
    ::= { cevPort 185 }

-- Unapproved 10 Gigabit Ethernet

cevPortGigBaseWdmRxOnly  OBJECT IDENTIFIER
    ::= { cevPort 186 }

-- WDM Rx ONLY Giga Ethernet

cevPortGigBaseDwdm3033  OBJECT IDENTIFIER
    ::= { cevPort 187 }

-- DWDM 3033 Giga Ethernet

cevPortGigBaseDwdm3112  OBJECT IDENTIFIER
    ::= { cevPort 188 }

-- DWDM 3112 Giga Ethernet

cevPortGigBaseDwdm3190  OBJECT IDENTIFIER
    ::= { cevPort 189 }

-- DWDM 3190 Giga Ethernet

cevPortGigBaseDwdm3268  OBJECT IDENTIFIER
    ::= { cevPort 190 }

-- DWDM 3268 Giga Ethernet

cevPortGigBaseDwdm3425  OBJECT IDENTIFIER
    ::= { cevPort 191 }

-- DWDM 3425 Giga Ethernet

cevPortGigBaseDwdm3504  OBJECT IDENTIFIER
    ::= { cevPort 192 }

-- DWDM 3504 Giga Ethernet

cevPortGigBaseDwdm3582  OBJECT IDENTIFIER
    ::= { cevPort 193 }

-- DWDM 3582 Giga Ethernet

cevPortGigBaseDwdm3661  OBJECT IDENTIFIER
    ::= { cevPort 194 }

-- DWDM 3661 Giga Ethernet

cevPortGigBaseDwdm3819  OBJECT IDENTIFIER
    ::= { cevPort 195 }

-- DWDM 3819 Giga Ethernet

cevPortGigBaseDwdm3898  OBJECT IDENTIFIER
    ::= { cevPort 196 }

-- DWDM 3898 Giga Ethernet

cevPortGigBaseDwdm3977  OBJECT IDENTIFIER
    ::= { cevPort 197 }

-- DWDM 3977 Giga Ethernet

cevPortGigBaseDwdm4056  OBJECT IDENTIFIER
    ::= { cevPort 198 }

-- DWDM 4056 Giga Ethernet

cevPortGigBaseDwdm4214  OBJECT IDENTIFIER
    ::= { cevPort 199 }

-- DWDM 4214 Giga Ethernet

cevPortGigBaseDwdm4294  OBJECT IDENTIFIER
    ::= { cevPort 200 }

-- DWDM 4294 Giga Ethernet

cevPortGigBaseDwdm4373  OBJECT IDENTIFIER
    ::= { cevPort 201 }

-- DWDM 4373 Giga Ethernet

cevPortGigBaseDwdm4453  OBJECT IDENTIFIER
    ::= { cevPort 202 }

-- DWDM 4453 Giga Ethernet

cevPortGigBaseDwdm4612  OBJECT IDENTIFIER
    ::= { cevPort 203 }

-- DWDM 4612 Giga Ethernet

cevPortGigBaseDwdm4692  OBJECT IDENTIFIER
    ::= { cevPort 204 }

-- DWDM 4692 Giga Ethernet

cevPortGigBaseDwdm4772  OBJECT IDENTIFIER
    ::= { cevPort 205 }

-- DWDM 4772 Giga Ethernet

cevPortGigBaseDwdm4851  OBJECT IDENTIFIER
    ::= { cevPort 206 }

-- DWDM 4851 Giga Ethernet

cevPortGigBaseDwdm5012  OBJECT IDENTIFIER
    ::= { cevPort 207 }

-- DWDM 5012 Giga Ethernet

cevPortGigBaseDwdm5092  OBJECT IDENTIFIER
    ::= { cevPort 208 }

-- DWDM 5092 Giga Ethernet

cevPortGigBaseDwdm5172  OBJECT IDENTIFIER
    ::= { cevPort 209 }

-- DWDM 5172 Giga Ethernet

cevPortGigBaseDwdm5252  OBJECT IDENTIFIER
    ::= { cevPort 210 }

-- DWDM 5252 Giga Ethernet

cevPortGigBaseDwdm5413  OBJECT IDENTIFIER
    ::= { cevPort 211 }

-- DWDM 5413 Giga Ethernet

cevPortGigBaseDwdm5494  OBJECT IDENTIFIER
    ::= { cevPort 212 }

-- DWDM 5494 Giga Ethernet

cevPortGigBaseDwdm5575  OBJECT IDENTIFIER
    ::= { cevPort 213 }

-- DWDM 5575 Giga Ethernet

cevPortGigBaseDwdm5655  OBJECT IDENTIFIER
    ::= { cevPort 214 }

-- DWDM 5655 Giga Ethernet

cevPortGigBaseDwdm5817  OBJECT IDENTIFIER
    ::= { cevPort 215 }

-- DWDM 5817 Giga Ethernet

cevPortGigBaseDwdm5898  OBJECT IDENTIFIER
    ::= { cevPort 216 }

-- DWDM 5898 Giga Ethernet

cevPortGigBaseDwdm5979  OBJECT IDENTIFIER
    ::= { cevPort 217 }

-- DWDM 5979 Giga Ethernet

cevPortGigBaseDwdm6061  OBJECT IDENTIFIER
    ::= { cevPort 218 }

-- DWDM 6061 Giga Ethernet

cevPort10GigBaseWdmRxOnly  OBJECT IDENTIFIER
    ::= { cevPort 219 }

-- 10 Gigabit Ethernet WDM Rx ONLY Xenpak Module

cevPort10GigBaseDwdm3033  OBJECT IDENTIFIER
    ::= { cevPort 220 }

-- 10 Gigabit Ethernet 3033 Laser Xenpak Module

cevPort10GigBaseDwdm3112  OBJECT IDENTIFIER
    ::= { cevPort 221 }

-- 10 Gigabit Ethernet 3112 Laser Xenpak Module

cevPort10GigBaseDwdm3190  OBJECT IDENTIFIER
    ::= { cevPort 222 }

-- 10 Gigabit Ethernet 3190 Laser Xenpak Module

cevPort10GigBaseDwdm3268  OBJECT IDENTIFIER
    ::= { cevPort 223 }

-- 10 Gigabit Ethernet 3268 Laser Xenpak Module

cevPort10GigBaseDwdm3425  OBJECT IDENTIFIER
    ::= { cevPort 224 }

-- 10 Gigabit Ethernet 3425 Laser Xenpak Module

cevPort10GigBaseDwdm3504  OBJECT IDENTIFIER
    ::= { cevPort 225 }

-- 10 Gigabit Ethernet 3504 Laser Xenpak Module

cevPort10GigBaseDwdm3582  OBJECT IDENTIFIER
    ::= { cevPort 226 }

-- 10 Gigabit Ethernet 3582 Laser Xenpak Module

cevPort10GigBaseDwdm3661  OBJECT IDENTIFIER
    ::= { cevPort 227 }

-- 10 Gigabit Ethernet 3661 Laser Xenpak Module

cevPort10GigBaseDwdm3819  OBJECT IDENTIFIER
    ::= { cevPort 228 }

-- 10 Gigabit Ethernet 3819 Laser Xenpak Module

cevPort10GigBaseDwdm3898  OBJECT IDENTIFIER
    ::= { cevPort 229 }

-- 10 Gigabit Ethernet 3898 Laser Xenpak Module

cevPort10GigBaseDwdm3977  OBJECT IDENTIFIER
    ::= { cevPort 230 }

-- 10 Gigabit Ethernet 3977 Laser Xenpak Module

cevPort10GigBaseDwdm4056  OBJECT IDENTIFIER
    ::= { cevPort 231 }

-- 10 Gigabit Ethernet 4056 Laser Xenpak Module

cevPort10GigBaseDwdm4214  OBJECT IDENTIFIER
    ::= { cevPort 232 }

-- 10 Gigabit Ethernet 4214 Laser Xenpak Module

cevPort10GigBaseDwdm4294  OBJECT IDENTIFIER
    ::= { cevPort 233 }

-- 10 Gigabit Ethernet 4294 Laser Xenpak Module

cevPort10GigBaseDwdm4373  OBJECT IDENTIFIER
    ::= { cevPort 234 }

-- 10 Gigabit Ethernet 4373 Laser Xenpak Module

cevPort10GigBaseDwdm4453  OBJECT IDENTIFIER
    ::= { cevPort 235 }

-- 10 Gigabit Ethernet 4453 Laser Xenpak Module

cevPort10GigBaseDwdm4612  OBJECT IDENTIFIER
    ::= { cevPort 236 }

-- 10 Gigabit Ethernet 4612 Laser Xenpak Module

cevPort10GigBaseDwdm4692  OBJECT IDENTIFIER
    ::= { cevPort 237 }

-- 10 Gigabit Ethernet 4692 Laser Xenpak Module

cevPort10GigBaseDwdm4772  OBJECT IDENTIFIER
    ::= { cevPort 238 }

-- 10 Gigabit Ethernet 4772 Laser Xenpak Module

cevPort10GigBaseDwdm4851  OBJECT IDENTIFIER
    ::= { cevPort 239 }

-- 10 Gigabit Ethernet 4851 Laser Xenpak Module

cevPort10GigBaseDwdm5012  OBJECT IDENTIFIER
    ::= { cevPort 240 }

-- 10 Gigabit Ethernet 5012 Laser Xenpak Module

cevPort10GigBaseDwdm5092  OBJECT IDENTIFIER
    ::= { cevPort 241 }

-- 10 Gigabit Ethernet 5092 Laser Xenpak Module

cevPort10GigBaseDwdm5172  OBJECT IDENTIFIER
    ::= { cevPort 242 }

-- 10 Gigabit Ethernet 5172 Laser Xenpak Module

cevPort10GigBaseDwdm5252  OBJECT IDENTIFIER
    ::= { cevPort 243 }

-- 10 Gigabit Ethernet 5252 Laser Xenpak Module

cevPort10GigBaseDwdm5413  OBJECT IDENTIFIER
    ::= { cevPort 244 }

-- 10 Gigabit Ethernet 5413 Laser Xenpak Module

cevPort10GigBaseDwdm5494  OBJECT IDENTIFIER
    ::= { cevPort 245 }

-- 10 Gigabit Ethernet 5494 Laser Xenpak Module

cevPort10GigBaseDwdm5575  OBJECT IDENTIFIER
    ::= { cevPort 246 }

-- 10 Gigabit Ethernet 5575 Laser Xenpak Module

cevPort10GigBaseDwdm5655  OBJECT IDENTIFIER
    ::= { cevPort 247 }

-- 10 Gigabit Ethernet 5655 Laser Xenpak Module

cevPort10GigBaseDwdm5817  OBJECT IDENTIFIER
    ::= { cevPort 248 }

-- 10 Gigabit Ethernet 5817 Laser Xenpak Module

cevPort10GigBaseDwdm5898  OBJECT IDENTIFIER
    ::= { cevPort 249 }

-- 10 Gigabit Ethernet 5898 Laser Xenpak Module

cevPort10GigBaseDwdm5979  OBJECT IDENTIFIER
    ::= { cevPort 250 }

-- 10 Gigabit Ethernet 5979 Laser Xenpak Module

cevPort10GigBaseDwdm6061  OBJECT IDENTIFIER
    ::= { cevPort 251 }

-- 10 Gigabit Ethernet 6061 Laser Xenpak Module

cevPortGigBaseBX10D  OBJECT IDENTIFIER
    ::= { cevPort 252 }

-- Giga Ethernet bidirectional 10km Downlink over SMF

cevPortGigBaseBX10U  OBJECT IDENTIFIER
    ::= { cevPort 253 }

-- Giga Ethernet bidirectional 10km uplink over SMF

cevPortT1E1  OBJECT IDENTIFIER
    ::= { cevPort 254 }

-- 8 port T1/E1 Shared Port Adapter

cevPort2GFCPhy  OBJECT IDENTIFIER
    ::= { cevPort 255 }

-- Optical port that is capable of transporting 2x Fibre Channel traffic

cevPortLanWirelessApplication  OBJECT IDENTIFIER
    ::= { cevPort 256 }

-- LAN wireless application interface

cevPortSEInternalFE  OBJECT IDENTIFIER
    ::= { cevPort 257 }

-- Internal FastEthernet interface in NM-SE - Service Engine Port adapter

cevPortCEInternalFE  OBJECT IDENTIFIER
    ::= { cevPort 258 }

-- Internal FastEthernet interface in NMD-CE-HP - Content Engine Port adapter

cevPortIpsecVpn  OBJECT IDENTIFIER
    ::= { cevPort 259 }

-- IPsec VPN Service interface

cevPortSsl  OBJECT IDENTIFIER
    ::= { cevPort 260 }

-- Ssl interface

cevPortFirewall  OBJECT IDENTIFIER
    ::= { cevPort 261 }

-- Firewall interface

cevPortDsp5441  OBJECT IDENTIFIER
    ::= { cevPort 263 }

-- DSP Processor for CMM T1/E1/FXS cards

cevPortDsp6415  OBJECT IDENTIFIER
    ::= { cevPort 264 }

-- DSP Processor for CMM ACT cards.(Communication Media Module)

cevPortHwicSerial  OBJECT IDENTIFIER
    ::= { cevPort 265 }

-- HWIC Serial Communication Controller

cevPortAsi  OBJECT IDENTIFIER
    ::= { cevPort 266 }

-- DVB ASI port

cevPortQam  OBJECT IDENTIFIER
    ::= { cevPort 267 }

-- QAM (Quadrature Amplitude Modulation) port with 2 channels each

cevPortGigBaseBT  OBJECT IDENTIFIER
    ::= { cevPort 268 }

-- 1000Base-T GBIC with less power requirement

cevPort100BaseUnknown  OBJECT IDENTIFIER
    ::= { cevPort 269 }

-- Unknown Fiber Fast Ethernet

cevPort100BaseUnapproved  OBJECT IDENTIFIER
    ::= { cevPort 270 }

-- Unapproved Fiber Fast Ethernet

cevPort100BaseBX10D  OBJECT IDENTIFIER
    ::= { cevPort 271 }

-- Fiber Fast Ethernet bi-directional 10km Downlink over SMF

cevPort100BaseBX10U  OBJECT IDENTIFIER
    ::= { cevPort 272 }

-- Fiber Fast Ethernet bi-directional 10km Uplink over SMF

cevPort100BaseFX  OBJECT IDENTIFIER
    ::= { cevPort 273 }

-- Fiber Fast Ethernet

cevPort100BaseLX10  OBJECT IDENTIFIER
    ::= { cevPort 274 }

-- Long Wave Fiber Fast Ethernet 10km over SMF

cevPort100BaseSX  OBJECT IDENTIFIER
    ::= { cevPort 275 }

-- Short Wave Fiber Fast Ethernet

cevPortSM  OBJECT IDENTIFIER
    ::= { cevPort 276 }

-- All the Service Modules (such as NM-CE-BP, NM-CIDS etc) that have IDBTYPE_SERVICE_MODULE hwidb type

cevPortT3E3  OBJECT IDENTIFIER
    ::= { cevPort 277 }

-- T3/E3 Shared Port Adapter interface.

cevPortMultiRate  OBJECT IDENTIFIER
    ::= { cevPort 278 }

-- Optical port that is capable of transporting Multirate traffic

cevPortWaveSonetPhy  OBJECT IDENTIFIER
    ::= { cevPort 279 }

-- Optical port that is capable of transporting OC-48 traffic in the ITU DWDM grid wavelength

cevPortSDCC  OBJECT IDENTIFIER
    ::= { cevPort 280 }

-- SDCC port that is an IP capable interface

cevPortAdslAnnexA  OBJECT IDENTIFIER
    ::= { cevPort 281 }

-- ADSL Annex A

cevPortAdslAnnexB  OBJECT IDENTIFIER
    ::= { cevPort 282 }

-- ADSL Annex B

cevPort10GigBaseZR  OBJECT IDENTIFIER
    ::= { cevPort 285 }

-- 1530-1565nm TDM 10G Module

cevPort10GigBaseCX4  OBJECT IDENTIFIER
    ::= { cevPort 286 }

-- Copper (15m) 10G Module

cevPort10GigBaseSR  OBJECT IDENTIFIER
    ::= { cevPort 287 }

-- 850nm MMF 10G Module

cevPortGigBaseCwdm1610  OBJECT IDENTIFIER
    ::= { cevPort 288 }

-- 1610nm color coded CWDM SFP

cevPortGigBaseCwdm1590  OBJECT IDENTIFIER
    ::= { cevPort 289 }

-- 1590nm color coded CWDM SFP

cevPortGigBaseCwdm1550  OBJECT IDENTIFIER
    ::= { cevPort 290 }

-- 1550nm color coded CWDM SFP

cevPortGigBaseCwdm1530  OBJECT IDENTIFIER
    ::= { cevPort 291 }

-- 1530nm color coded CWDM SFP

cevPortGigBaseCwdm1510  OBJECT IDENTIFIER
    ::= { cevPort 292 }

-- 1510nm color coded CWDM SFP

cevPortGigBaseCwdm1490  OBJECT IDENTIFIER
    ::= { cevPort 293 }

-- 1490nm color coded CWDM SFP

cevPortGigBaseCwdm1470  OBJECT IDENTIFIER
    ::= { cevPort 294 }

-- 1470nm color coded CWDM SFP

cevPortGigBaseCwdm1570  OBJECT IDENTIFIER
    ::= { cevPort 295 }

-- 1570nm color coded CWDM SFP

cevPortUSB  OBJECT IDENTIFIER
    ::= { cevPort 296 }

-- Universal Serial Bus (USB) interface

cevPortSslVpn  OBJECT IDENTIFIER
    ::= { cevPort 297 }

-- Web/VPN interface

cevPortCableModem  OBJECT IDENTIFIER
    ::= { cevPort 298 }

-- Cable modem port

cevNmeApaPort  OBJECT IDENTIFIER
    ::= { cevPort 299 }

-- Service Classification Element Port for NME-APA.

cevPort10GigBase  OBJECT IDENTIFIER
    ::= { cevPort 300 }

-- 300m over 50um MMF and 220m over FDDI grade MMF 10G Module

cevPort10GigBaseLRM  OBJECT IDENTIFIER
    ::= { cevPort 301 }

-- 300m over 50um MMF and 220m over FDDI grade MMF 10G Module

cevPortdot11abg  OBJECT IDENTIFIER
    ::= { cevPort 302 }

-- 802.11G Radio

cevPortDti  OBJECT IDENTIFIER
    ::= { cevPort 303 }

-- DOCSIS Timing, Communication, and Control Plus port for DTI module

cevPort10GigSFPPlus  OBJECT IDENTIFIER
    ::= { cevPort 304 }

-- a type of 10GE port that can take a variety of tranceivers fitting the SFP+ Multi Source Agreement form factor

cevPortCscPort  OBJECT IDENTIFIER
    ::= { cevPort 305 }

-- Virtual ports on either end of the link that connects the user side with network side on a service control entity

cevPortGEXFP  OBJECT IDENTIFIER
    ::= { cevPort 306 }

-- Ten GigabitEthernet Port

cevPortGigBaseDwdm6141  OBJECT IDENTIFIER
    ::= { cevPort 307 }

-- DWDM 6141 Giga Ethernet SFP

cevPortGigBaseDwdm5736  OBJECT IDENTIFIER
    ::= { cevPort 308 }

-- DWDM 5736 Giga Ethernet SFP

cevPortGigBaseDwdm5332  OBJECT IDENTIFIER
    ::= { cevPort 309 }

-- DWDM 5332 Giga Ethernet SFP

cevPortGigBaseDwdm4931  OBJECT IDENTIFIER
    ::= { cevPort 310 }

-- DWDM 4931 Giga Ethernet SFP

cevPortGigBaseDwdm4532  OBJECT IDENTIFIER
    ::= { cevPort 311 }

-- DWDM 4532 Giga Ethernet SFP

cevPortGigBaseDwdm4134  OBJECT IDENTIFIER
    ::= { cevPort 312 }

-- DWDM 4134 Giga Ethernet SFP

cevPortGigBaseDwdm3739  OBJECT IDENTIFIER
    ::= { cevPort 313 }

-- DWDM 3739 Giga Ethernet SFP

cevPortGigBaseDwdm3346  OBJECT IDENTIFIER
    ::= { cevPort 314 }

-- DWDM 3346 Giga Ethernet SFP

cevPort10GigEthernet  OBJECT IDENTIFIER
    ::= { cevPort 315 }

-- 10 Gigabit Ethernet interface

cevPortSEInternal  OBJECT IDENTIFIER
    ::= { cevPort 316 }

-- Virtual port of a Service Engine connecting the RP and the SE

cevPortGigBaseEX  OBJECT IDENTIFIER
    ::= { cevPort 317 }

-- 1000 Base EX Fiber Gigabit Ethernet

cevPort40GigEthernet  OBJECT IDENTIFIER
    ::= { cevPort 318 }

-- 40 Gigabit Ethernet interface

cevPortAces  OBJECT IDENTIFIER
    ::= { cevPort 319 }

-- Application Control Engine Service interface

cevPort40GigQSFPPlus  OBJECT IDENTIFIER
    ::= { cevPort 321 }

-- A type of 40GE port that can take a variety of transceivers fitting the QSFP + Multi Source Agreement form factor

cevPort100GECFP  OBJECT IDENTIFIER
    ::= { cevPort 322 }

-- a type of 100GE port that can take a variety of transceivers fitting the CFP Multi Source Agreement form factor

cevPortPlcG  OBJECT IDENTIFIER
    ::= { cevPort 323 }

-- PLC Generic Port

cevPortWimaxG  OBJECT IDENTIFIER
    ::= { cevPort 324 }

-- Wimax Generic Port

cevPort3gCdmaG  OBJECT IDENTIFIER
    ::= { cevPort 325 }

-- 3G CDMA Generic Port

cevPort3gGsmG  OBJECT IDENTIFIER
    ::= { cevPort 326 }

-- 3G GSM Generic Port

cevPortWpanG  OBJECT IDENTIFIER
    ::= { cevPort 327 }

-- WPAN Generic Port

cevPortSseBreakout100GePort  OBJECT IDENTIFIER
    ::= { cevPort 337 }

-- 100GE port available on the next generation of Cisco Network Processors used in Panini family or products

cevPortSseBreakout10GePort  OBJECT IDENTIFIER
    ::= { cevPort 338 }

-- 10GE port available on the next generation of Cisco Network Processors used in Panini family of products

cevPortCisco10GeSFPPlusPOZR  OBJECT IDENTIFIER
    ::= { cevPort 339 }

-- Cisco SFP-10G-ZR Cable: 9 micron singlemode Wavelength: 1550nm

cevPortCisco10GeSFPPlusPOER  OBJECT IDENTIFIER
    ::= { cevPort 340 }

-- Cisco SFP-10G-ER Cable: 9 micron singlemode Wavelength: 1550nm

cevPortCisco10GeSFPPlusPOSRX  OBJECT IDENTIFIER
    ::= { cevPort 341 }

-- Cisco SFP-10G-SR-X Cable: 50 micron multimode Wavelength: 850nm

cevPortCisco10GeSFPPlusPOLRX  OBJECT IDENTIFIER
    ::= { cevPort 342 }

-- Cisco SFP-10G-LR-X Cable: 9 micron singlemode Wavelength: 1310nm

cevPortCisco10GeSFPPlusPOLR  OBJECT IDENTIFIER
    ::= { cevPort 343 }

-- Cisco SFP-10G-LR Cable: 9 micron singlemode Wavelength: 1310nm

cevPortCisco10GeSFPPlusPOSR  OBJECT IDENTIFIER
    ::= { cevPort 344 }

-- Cisco SFP-10G-SR Cable: 50 micron multimode Wavelength: 850nm

cevPortPHwicSerial  OBJECT IDENTIFIER
    ::= { cevPort 346 }

-- 16-Port Async HWIC

cevPortPT1E1  OBJECT IDENTIFIER
    ::= { cevPort 347 }

-- 2 port channelized T1/E1, and PRI HWIC (data only)

cevPortPHdvDsp  OBJECT IDENTIFIER
    ::= { cevPort 348 }

-- 128-channel high-density voice and video DSP module

cevStack  OBJECT IDENTIFIER
    ::= { cevMIBObjects 11 }

cevStackUnknown  OBJECT IDENTIFIER
    ::= { cevStack 1 }

cevStackCat37xx  OBJECT IDENTIFIER
    ::= { cevStack 2 }

-- The type of stacking used for Catalyst 37xx stack-able switch product

cevCat65xxVirtualSwitch  OBJECT IDENTIFIER
    ::= { cevStack 3 }

-- Catalyst 65xx Virtual Switch product

cevCbs3120Stack  OBJECT IDENTIFIER
    ::= { cevStack 5 }

-- CBS3120-stack: A stack of CBS3120 switch modules

cevC29xxStack  OBJECT IDENTIFIER
    ::= { cevStack 11 }

-- A stack of C29XX switch modules

cevStackIosXrMultichassis  OBJECT IDENTIFIER
    ::= { cevStack 12 }

-- IOS-XR Multichassis virtual stack entity provides containment relationship of 2 or more IOS-XR chassis connected in a multi-chasiss setup

cevStackCat4xxxVirtualSwitchStack  OBJECT IDENTIFIER
    ::= { cevStack 13 }

-- catalyst 4xxx based virtual switching system stack

cevMidplane  OBJECT IDENTIFIER
    ::= { cevMIBObjects 12 }

-- Midplane of the chassis

cevMidplaneUmg9820  OBJECT IDENTIFIER
    ::= { cevMidplane 1 }


END
