-- *****************************************************************
-- CISCO-SWITCH-FABRIC-CAPABILITY.my:
-- Cisco CISCO-SWITCH-FABRIC-MIB AGENT-CAPABILITIES
--   
-- July 2013,  Liang Mei
--   
-- Copyright (c) 2012-2013 by Cisco Systems, Inc.
-- All rights reserved.
-- *****************************************************************

CISCO-SWITCH-FABRIC-CAPABILITY DEFINITIONS ::= BEGIN

IMPORTS
    MODULE-IDENTITY
        FROM SNMPv2-SMI
    AGENT-CAPABILITIES
        FROM SNMPv2-CONF
    ciscoAgentCapability
        FROM CISCO-SMI;


ciscoSwitchFabricCapability MODULE-IDENTITY
    LAST-UPDATED    "201307170000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of
        CISCO-SWITCH-FABRIC-MIB."
    REVISION        "201307170000Z"
    DESCRIPTION
        "Added capability statement
        ciscoSwitchFabricCapV15R0102SYPCat6K."
    REVISION        "201307100000Z"
    DESCRIPTION
        "Initial version of this MIB module."
    ::= { ciscoAgentCapability 618 }



ciscoSwitchFabricCapNxOSV06R0104PN7k AGENT-CAPABILITIES
    PRODUCT-RELEASE "Cisco NX-OS 6.1(4) on Nexus 7000 series devices."
    STATUS          current
    DESCRIPTION
        "CISCO-SWITCH-FABRIC-MIB capabilities."

    SUPPORTS        CISCO-SWITCH-FABRIC-MIB
    INCLUDES        { csfFabricUtilGroup }
    ::= { ciscoSwitchFabricCapability 1 }

ciscoSwitchFabricCapNxOSV06R0201PMds AGENT-CAPABILITIES
    PRODUCT-RELEASE "Cisco NX-OS 6.2(1) on MDS series devices."
    STATUS          current
    DESCRIPTION
        "CISCO-SWITCH-FABRIC-MIB capabilities."

    SUPPORTS        CISCO-SWITCH-FABRIC-MIB
    INCLUDES        { csfFabricUtilGroup }
    ::= { ciscoSwitchFabricCapability 2 }

ciscoSwitchFabricCapV15R0102SYPCat6K AGENT-CAPABILITIES
    PRODUCT-RELEASE "Cisco IOS 15.1(2)SY on Catalyst 6000/6500
                     series devices."
    STATUS          current
    DESCRIPTION
        "CISCO-SWITCH-FABRIC-MIB capabilities."

    SUPPORTS        CISCO-SWITCH-FABRIC-MIB
    INCLUDES        { csfFabricUtilGroup }
    ::= { ciscoSwitchFabricCapability 3 }

END
